;;; ================================================================
;;; BR_Insert.lsp  |  Brelje & Race CAD Tools  |  Block/Detail Insert
;;; ================================================================
;;; Requires: BR_Core.lsp loaded first.
;;; DCL file: BR_Insert.dcl (dialog name "br_insert")
;;; Command:  BR_INS
;;;
;;; Block database: 1077 blocks across 19 categories (generated from Blocks.csv).
;;; ================================================================


;;;; -- BLOCK DATABASE ----------------------------------------------
;;;;
;;;; Each entry: (display-name  block-name  category  target-layer  source-path)
;;;;
;;;; display-name  -- shown in the list box
;;;; block-name    -- actual DWG block name to insert
;;;; category      -- category string for filtering
;;;; target-layer  -- layer to set current before insert (or "" for current)
;;;; source-path   -- full path to source DWG if external, or "" if defined in drawing
;;;;
;;;; Block database generated from Blocks.csv (1077 blocks, 19 categories).

(setq *BR:BLK-ROOT* "J:\\LIB\\BR\\Palette Tools\\")

(setq *BR:BLOCKS*
  (list
    ;; -- ARROWS, GRADES & PAVEMENT MARKINGS (29 blocks) --
    (list "Arrow & Line - 1 or 2 ways" "ARR LINE" "Arrows, Grades & Pavement Markings" "0" "ARR LINE.dwg")
    (list "Fancy Arrow - Bearhead" "ARR BEARHEAD" "Arrows, Grades & Pavement Markings" "0" "ARR BEARHEAD.dwg")
    (list "Fancy Arrow - Dynamic" "ARR DYNAMIC" "Arrows, Grades & Pavement Markings" "0" "ARR DYNAMIC.dwg")
    (list "Standard Arrow" "ARR STANDARD" "Arrows, Grades & Pavement Markings" "0" "ARR STANDARD.DWG")
    (list "Fancy Arrow-Similar to Swale Arrow" "ARR SWALE" "Arrows, Grades & Pavement Markings" "0" "ARR SWALE.DWG")
    (list "Architectural Arrow" "ARR ARCHITECTURAL" "Arrows, Grades & Pavement Markings" "0" "ARR ARCHITECTURAL.DWG")
    (list "Hydrology Arrow" "ARR HYDRO" "Arrows, Grades & Pavement Markings" "0" "ARR HYDRO.dwg")
    (list "Flow Arrow - Dynamic" "ARR FLOW2" "Arrows, Grades & Pavement Markings" "0" "ARR FLOW2.dwg")
    (list "2, 3 or 4 Arrow's & Percent" "ARR ARROWS PERCENT" "Arrows, Grades & Pavement Markings" "0" "ARR ARROWS PERCENT.DWG")
    (list "Project Site Arrow" "ARR PROJECT" "Arrows, Grades & Pavement Markings" "0" "ARR PROJECT.dwg")
    (list "Star" "STAR" "Arrows, Grades & Pavement Markings" "0" "STAR.dwg")
    (list "Label with Leader - LEFT" "LABEL WITH LEADER" "Arrows, Grades & Pavement Markings" "0" "LABEL WITH LEADER.dwg")
    (list "Label with Leader - RIGHT" "LABEL WITH LEADER" "Arrows, Grades & Pavement Markings" "0" "LABEL WITH LEADER.dwg")
    (list "Grade Stick - LEFT & RIGHT" "GRADE STICK" "Arrows, Grades & Pavement Markings" "0" "GRADE STICK.dwg")
    (list "Grade Stick - LONG DESCRIPTION" "GRADE STICK LONG DESCRIPTION" "Arrows, Grades & Pavement Markings" "0" "GRADE STICK LONG DESCRIPTION.dwg")
    (list "Directional Arrow & Text - LEFT" "ARR DIRECTIONAL2 LT" "Arrows, Grades & Pavement Markings" "0" "ARR DIRECTIONAL2 LT.dwg")
    (list "Directional Arrow & Text - RIGHT" "ARR DIRECTIONAL2 RT" "Arrows, Grades & Pavement Markings" "0" "ARR DIRECTIONAL2 RT.dwg")
    (list "Directional Arrow - LEFT" "ARR DIRECTIONAL1 LT" "Arrows, Grades & Pavement Markings" "0" "ARR DIRECTIONAL1 LT.dwg")
    (list "Directional Arrow - RIGHT" "ARR DIRECTIONAL1 RT" "Arrows, Grades & Pavement Markings" "0" "ARR DIRECTIONAL1 RT.dwg")
    (list "Multi Grade Stick - LEFT" "GRADE STICK2 LT" "Arrows, Grades & Pavement Markings" "0" "GRADE STICK2 LT.dwg")
    (list "Multi Grade Stick - RIGHT" "GRADE STICK2 RT" "Arrows, Grades & Pavement Markings" "0" "GRADE STICK2 RT.dwg")
    (list "Pavement Marking Arrow - LEFT" "PAINT ARR LT" "Arrows, Grades & Pavement Markings" "0" "PAINT ARR LT.DWG")
    (list "Pavement Marking Arrow - RIGHT" "PAINT ARR RT" "Arrows, Grades & Pavement Markings" "0" "PAINT ARR RT.DWG")
    (list "Pavement Marking Arrow - STRAIGHT" "PAINT ARR STRAIGHT" "Arrows, Grades & Pavement Markings" "0" "PAINT ARR STRAIGHT.dwg")
    (list "Pavement Marking Arrow - Caltrans - LEFT" "PAINT ARR CALTRANS LT" "Arrows, Grades & Pavement Markings" "0" "PAINT ARR CALTRANS LT.dwg")
    (list "Pavement Marking Arrow - Caltrans - RIGHT" "PAINT ARR CALTRANS RT" "Arrows, Grades & Pavement Markings" "0" "PAINT ARR CALTRANS RT.dwg")
    (list "Pavement Marking Arrow - MERGE" "PAINT ARR MERGE" "Arrows, Grades & Pavement Markings" "0" "PAINT ARR MERGE.dwg")
    (list "Pavement Marking - ADA" "PAINT HC" "Arrows, Grades & Pavement Markings" "0" "PAINT HC.dwg")
    (list "Pavement Marking - STOP" "PAINT STOP" "Arrows, Grades & Pavement Markings" "0" "PAINT STOP.dwg")
    ;; -- CITYCOUNTY (12 blocks) --
    (list "Sonoma County - Seal" "LOGO COUNTY SEAL" "CityCounty" "0" "LOGO COUNTY SEAL.dwg")
    (list "Sonoma County - Standard Note Sheet for Subdivisions" "NOTE COUNTY ENTIRE SHEET" "CityCounty" "0" "NOTE COUNTY ENTIRE SHEET.dwg")
    (list "Sonoma County - Standard Note Sheet for Grading Permits" "NOTE COUNTY ENTIRE SHEET-GRADING PERMIT" "CityCounty" "0" "NOTE COUNTY ENTIRE SHEET-GRADING PERMIT.dwg")
    (list "Sonoma County - Record Plan Note" "SIGNATURE COUNTY RECORD PLAN" "CityCounty" "0" "SIGNATURE COUNTY RECORD PLAN.dwg")
    (list "Town Of Windsor - Public Water Signature Block" "SIGNATURE TOW APP PUB WTR" "CityCounty" "0" "SIGNATURE TOW APP PUB WTR.dwg")
    (list "Santa Rosa - Public Works Signature Block" "SIGNATURE SR APP FOR CONST" "CityCounty" "0" "SIGNATURE SR APP FOR CONST.dwg")
    (list "Santa Rosa - Approved By - Fire, Utilities, Project Engineer" "SIGNATURE SR APP FIRE UTIL ENGR" "CityCounty" "0" "SIGNATURE SR APP FIRE UTIL ENGR.DWG")
    (list "Santa Rosa - Record Plan Data" "SIGNATURE SR RECORD PLAN DATA" "CityCounty" "0" "SIGNATURE SR RECORD PLAN DATA.dwg")
    (list "Santa Rosa - Record Plan Note" "SIGNATURE SR RECORD PLAN" "CityCounty" "0" "SIGNATURE SR RECORD PLAN.dwg")
    (list "Petaluma Signature Block" "SIGNATURE PETALUMA APP FOR CONST" "CityCounty" "0" "SIGNATURE PETALUMA APP FOR CONST.dwg")
    (list "Local Fire Authority Review" "SIGNATURE LOCAL FIRE REVIEW" "CityCounty" "0" "SIGNATURE LOCAL FIRE REVIEW.dwg")
    (list "Lake County - Record Plan Note" "SIGNATURE LAKE COUNTY RECORD PLAN" "CityCounty" "0" "SIGNATURE LAKE COUNTY RECORD PLAN.dwg")
    ;; -- DIP-STEEL-FITTING (278 blocks) --
    (list "00 PIPE BREAK" "00 PIPE BREAK" "DIP-STEEL-Fitting" "0" "00 PIPE BREAK.dwg")
    (list "00 PIPE SECTION" "00 PIPE SECTION" "DIP-STEEL-Fitting" "0" "00 PIPE SECTION.dwg")
    (list "00 FLOW METER FLG" "00 FLOW METER FLG" "DIP-STEEL-Fitting" "0" "00 FLOW METER FLG.dwg")
    (list "00 SPOOL FLG" "00 SPOOL FLG" "DIP-STEEL-Fitting" "0" "00 SPOOL FLG.dwg")
    (list "02 CHECK WAFER" "02 CHECK WAFER" "DIP-STEEL-Fitting" "0" "02 CHECK WAFER.dwg")
    (list "02 EL 90 DN FLG" "02 EL 90 DN FLG" "DIP-STEEL-Fitting" "0" "02 EL 90 DN FLG.dwg")
    (list "02 EL 90 FLG" "02 EL 90 FLG" "DIP-STEEL-Fitting" "0" "02 EL 90 FLG.dwg")
    (list "02 EL 90 UP FLG" "02 EL 90 UP FLG" "DIP-STEEL-Fitting" "0" "02 EL 90 UP FLG.dwg")
    (list "02 FLG" "02 FLG" "DIP-STEEL-Fitting" "0" "02 FLG.dwg")
    (list "02 GATE FLG" "02 GATE FLG" "DIP-STEEL-Fitting" "0" "02 GATE FLG.dwg")
    (list "02 TEE FLG" "02 TEE FLG" "DIP-STEEL-Fitting" "0" "02 TEE FLG.dwg")
    (list "02 TEE UP FLG" "02 TEE UP FLG" "DIP-STEEL-Fitting" "0" "02 TEE UP FLG.dwg")
    (list "03 ADP MJxFLG" "03 ADP MJxFLG" "DIP-STEEL-Fitting" "0" "03 ADP MJxFLG.dwg")
    (list "03 BTFY FLG" "03 BTFY FLG" "DIP-STEEL-Fitting" "0" "03 BTFY FLG.dwg")
    (list "03 CROSS FLG" "03 CROSS FLG" "DIP-STEEL-Fitting" "0" "03 CROSS FLG.dwg")
    (list "03 EL 11 FLG" "03 EL 11 FLG" "DIP-STEEL-Fitting" "0" "03 EL 11 FLG.dwg")
    (list "03 EL 11 FLGxMJ" "03 EL 11 FLGxMJ" "DIP-STEEL-Fitting" "0" "03 EL 11 FLGxMJ.dwg")
    (list "03 EL 11 MJ" "03 EL 11 MJ" "DIP-STEEL-Fitting" "0" "03 EL 11 MJ.dwg")
    (list "03 EL 22 DN FLG" "03 EL 22 DN FLG" "DIP-STEEL-Fitting" "0" "03 EL 22 DN FLG.dwg")
    (list "03 EL 22 FLG" "03 EL 22 FLG" "DIP-STEEL-Fitting" "0" "03 EL 22 FLG.dwg")
    (list "03 EL 22 FLGxMJ" "03 EL 22 FLGxMJ" "DIP-STEEL-Fitting" "0" "03 EL 22 FLGxMJ.dwg")
    (list "03 EL 22 MJ" "03 EL 22 MJ" "DIP-STEEL-Fitting" "0" "03 EL 22 MJ.dwg")
    (list "03 EL 22 UP FLG" "03 EL 22 UP FLG" "DIP-STEEL-Fitting" "0" "03 EL 22 UP FLG.dwg")
    (list "03 EL 45 DN FLG" "03 EL 45 DN FLG" "DIP-STEEL-Fitting" "0" "03 EL 45 DN FLG.dwg")
    (list "03 EL 45 FLG" "03 EL 45 FLG" "DIP-STEEL-Fitting" "0" "03 EL 45 FLG.dwg")
    (list "03 EL 45 FLGxMJ" "03 EL 45 FLGxMJ" "DIP-STEEL-Fitting" "0" "03 EL 45 FLGxMJ.dwg")
    (list "03 EL 45 MJ" "03 EL 45 MJ" "DIP-STEEL-Fitting" "0" "03 EL 45 MJ.dwg")
    (list "03 EL 45 UP FLG" "03 EL 45 UP FLG" "DIP-STEEL-Fitting" "0" "03 EL 45 UP FLG.dwg")
    (list "03 EL 90 DN FLG" "03 EL 90 DN FLG" "DIP-STEEL-Fitting" "0" "03 EL 90 DN FLG.dwg")
    (list "03 EL 90 FLG" "03 EL 90 FLG" "DIP-STEEL-Fitting" "0" "03 EL 90 FLG.dwg")
    (list "03 EL 90 FLGxMJ" "03 EL 90 FLGxMJ" "DIP-STEEL-Fitting" "0" "03 EL 90 FLGxMJ.dwg")
    (list "03 EL 90 MJ" "03 EL 90 MJ" "DIP-STEEL-Fitting" "0" "03 EL 90 MJ.dwg")
    (list "03 EL 90 UP FLG" "03 EL 90 UP FLG" "DIP-STEEL-Fitting" "0" "03 EL 90 UP FLG.dwg")
    (list "03 FCA FLG" "03 FCA FLG" "DIP-STEEL-Fitting" "0" "03 FCA FLG.dwg")
    (list "03 FLG" "03 FLG" "DIP-STEEL-Fitting" "0" "03 FLG.dwg")
    (list "03 GATE FLG" "03 GATE FLG" "DIP-STEEL-Fitting" "0" "03 GATE FLG.dwg")
    (list "03 MJ" "03 MJ" "DIP-STEEL-Fitting" "0" "03 MJ.dwg")
    (list "03 PLUG FLG" "03 PLUG FLG" "DIP-STEEL-Fitting" "0" "03 PLUG FLG.dwg")
    (list "03 SLEEVE MJ" "03 SLEEVE MJ" "DIP-STEEL-Fitting" "0" "03 SLEEVE MJ.dwg")
    (list "03 TEE FLG" "03 TEE FLG" "DIP-STEEL-Fitting" "0" "03 TEE FLG.dwg")
    (list "03 TEE MJ" "03 TEE MJ" "DIP-STEEL-Fitting" "0" "03 TEE MJ.dwg")
    (list "03 TEE MJxMJxFLG" "03 TEE MJxMJxFLG" "DIP-STEEL-Fitting" "0" "03 TEE MJxMJxFLG.dwg")
    (list "03 TEE UP FLG" "03 TEE UP FLG" "DIP-STEEL-Fitting" "0" "03 TEE UP FLG.dwg")
    (list "04 ADP MJxFLG" "04 ADP MJxFLG" "DIP-STEEL-Fitting" "0" "04 ADP MJxFLG.dwg")
    (list "04 BTFY FLG" "04 BTFY FLG" "DIP-STEEL-Fitting" "0" "04 BTFY FLG.dwg")
    (list "04 CROSS FLG" "04 CROSS FLG" "DIP-STEEL-Fitting" "0" "04 CROSS FLG.dwg")
    (list "04 EL 11 FLG" "04 EL 11 FLG" "DIP-STEEL-Fitting" "0" "04 EL 11 FLG.dwg")
    (list "04 EL 11 FLGxMJ" "04 EL 11 FLGxMJ" "DIP-STEEL-Fitting" "0" "04 EL 11 FLGxMJ.dwg")
    (list "04 EL 11 MJ" "04 EL 11 MJ" "DIP-STEEL-Fitting" "0" "04 EL 11 MJ.dwg")
    (list "04 EL 22 DN FLG" "04 EL 22 DN FLG" "DIP-STEEL-Fitting" "0" "04 EL 22 DN FLG.dwg")
    (list "04 EL 22 FLG" "04 EL 22 FLG" "DIP-STEEL-Fitting" "0" "04 EL 22 FLG.dwg")
    (list "04 EL 22 FLGxMJ" "04 EL 22 FLGxMJ" "DIP-STEEL-Fitting" "0" "04 EL 22 FLGxMJ.dwg")
    (list "04 EL 22 MJ" "04 EL 22 MJ" "DIP-STEEL-Fitting" "0" "04 EL 22 MJ.dwg")
    (list "04 EL 22 UP FLG" "04 EL 22 UP FLG" "DIP-STEEL-Fitting" "0" "04 EL 22 UP FLG.dwg")
    (list "04 EL 45 DN FCA FLG" "04 EL 45 DN FCA FLG" "DIP-STEEL-Fitting" "0" "04 EL 45 DN FCA FLG.dwg")
    (list "04 EL 45 DN FLG" "04 EL 45 DN FLG" "DIP-STEEL-Fitting" "0" "04 EL 45 DN FLG.dwg")
    (list "04 EL 45 FLG" "04 EL 45 FLG" "DIP-STEEL-Fitting" "0" "04 EL 45 FLG.dwg")
    (list "04 EL 45 FLGxMJ" "04 EL 45 FLGxMJ" "DIP-STEEL-Fitting" "0" "04 EL 45 FLGxMJ.dwg")
    (list "04 EL 45 MJ" "04 EL 45 MJ" "DIP-STEEL-Fitting" "0" "04 EL 45 MJ.dwg")
    (list "04 EL 45 UP FLG" "04 EL 45 UP FLG" "DIP-STEEL-Fitting" "0" "04 EL 45 UP FLG.dwg")
    (list "04 EL 90 DN FLG" "04 EL 90 DN FLG" "DIP-STEEL-Fitting" "0" "04 EL 90 DN FLG.dwg")
    (list "04 EL 90 FLG" "04 EL 90 FLG" "DIP-STEEL-Fitting" "0" "04 EL 90 FLG.dwg")
    (list "04 EL 90 FLGxMJ" "04 EL 90 FLGxMJ" "DIP-STEEL-Fitting" "0" "04 EL 90 FLGxMJ.dwg")
    (list "04 EL 90 MJ" "04 EL 90 MJ" "DIP-STEEL-Fitting" "0" "04 EL 90 MJ.dwg")
    (list "04 EL 90 UP FLG" "04 EL 90 UP FLG" "DIP-STEEL-Fitting" "0" "04 EL 90 UP FLG.dwg")
    (list "04 FCA FLG" "04 FCA FLG" "DIP-STEEL-Fitting" "0" "04 FCA FLG.dwg")
    (list "04 FLG" "04 FLG" "DIP-STEEL-Fitting" "0" "04 FLG.dwg")
    (list "04 GATE FLG" "04 GATE FLG" "DIP-STEEL-Fitting" "0" "04 GATE FLG.dwg")
    (list "04 GATE MJxFLG" "04 GATE MJxFLG" "DIP-STEEL-Fitting" "0" "04 GATE MJxFLG.dwg")
    (list "04 MJ" "04 MJ" "DIP-STEEL-Fitting" "0" "04 MJ.dwg")
    (list "04 PLUG FLG" "04 PLUG FLG" "DIP-STEEL-Fitting" "0" "04 PLUG FLG.dwg")
    (list "04 SLEEVE MJ" "04 SLEEVE MJ" "DIP-STEEL-Fitting" "0" "04 SLEEVE MJ.dwg")
    (list "04 TEE FLG" "04 TEE FLG" "DIP-STEEL-Fitting" "0" "04 TEE FLG.dwg")
    (list "04 TEE MJ" "04 TEE MJ" "DIP-STEEL-Fitting" "0" "04 TEE MJ.dwg")
    (list "04 TEE MJxMJxFLG" "04 TEE MJxMJxFLG" "DIP-STEEL-Fitting" "0" "04 TEE MJxMJxFLG.dwg")
    (list "04 TEE UP FLG" "04 TEE UP FLG" "DIP-STEEL-Fitting" "0" "04 TEE UP FLG.dwg")
    (list "0403 RED FLG" "0403 RED FLG" "DIP-STEEL-Fitting" "0" "0403 RED FLG.dwg")
    (list "0403 RED FLGxMJ" "0403 RED FLGxMJ" "DIP-STEEL-Fitting" "0" "0403 RED FLGxMJ.dwg")
    (list "0403 RED MJ" "0403 RED MJ" "DIP-STEEL-Fitting" "0" "0403 RED MJ.dwg")
    (list "0403 RED MJxFLG" "0403 RED MJxFLG" "DIP-STEEL-Fitting" "0" "0403 RED MJxFLG.dwg")
    (list "040402 TEE FLG" "040402 TEE FLG" "DIP-STEEL-Fitting" "0" "040402 TEE FLG.dwg")
    (list "06 ADP MJxFLG" "06 ADP MJxFLG" "DIP-STEEL-Fitting" "0" "06 ADP MJxFLG.dwg")
    (list "06 BTFY FLG" "06 BTFY FLG" "DIP-STEEL-Fitting" "0" "06 BTFY FLG.dwg")
    (list "06 CROSS FLG" "06 CROSS FLG" "DIP-STEEL-Fitting" "0" "06 CROSS FLG.dwg")
    (list "06 EL 11 FLG" "06 EL 11 FLG" "DIP-STEEL-Fitting" "0" "06 EL 11 FLG.dwg")
    (list "06 EL 11 FLGxMJ" "06 EL 11 FLGxMJ" "DIP-STEEL-Fitting" "0" "06 EL 11 FLGxMJ.dwg")
    (list "06 EL 11 MJ" "06 EL 11 MJ" "DIP-STEEL-Fitting" "0" "06 EL 11 MJ.dwg")
    (list "06 EL 22 DN FLG" "06 EL 22 DN FLG" "DIP-STEEL-Fitting" "0" "06 EL 22 DN FLG.dwg")
    (list "06 EL 22 DN MJ" "06 EL 22 DN MJ" "DIP-STEEL-Fitting" "0" "06 EL 22 DN MJ.dwg")
    (list "06 EL 22 FLG" "06 EL 22 FLG" "DIP-STEEL-Fitting" "0" "06 EL 22 FLG.dwg")
    (list "06 EL 22 FLGxMJ" "06 EL 22 FLGxMJ" "DIP-STEEL-Fitting" "0" "06 EL 22 FLGxMJ.dwg")
    (list "06 EL 22 MJ" "06 EL 22 MJ" "DIP-STEEL-Fitting" "0" "06 EL 22 MJ.dwg")
    (list "06 EL 22 UP FLG" "06 EL 22 UP FLG" "DIP-STEEL-Fitting" "0" "06 EL 22 UP FLG.dwg")
    (list "06 EL 22 UP MJ" "06 EL 22 UP MJ" "DIP-STEEL-Fitting" "0" "06 EL 22 UP MJ.dwg")
    (list "06 EL 45 DN FLG" "06 EL 45 DN FLG" "DIP-STEEL-Fitting" "0" "06 EL 45 DN FLG.dwg")
    (list "06 EL 45 FLG" "06 EL 45 FLG" "DIP-STEEL-Fitting" "0" "06 EL 45 FLG.dwg")
    (list "06 EL 45 FLGxMJ" "06 EL 45 FLGxMJ" "DIP-STEEL-Fitting" "0" "06 EL 45 FLGxMJ.dwg")
    (list "06 EL 45 MJ" "06 EL 45 MJ" "DIP-STEEL-Fitting" "0" "06 EL 45 MJ.dwg")
    (list "06 EL 45 UP FLG" "06 EL 45 UP FLG" "DIP-STEEL-Fitting" "0" "06 EL 45 UP FLG.dwg")
    (list "06 EL 90 DN FLG" "06 EL 90 DN FLG" "DIP-STEEL-Fitting" "0" "06 EL 90 DN FLG.dwg")
    (list "06 EL 90 FLG" "06 EL 90 FLG" "DIP-STEEL-Fitting" "0" "06 EL 90 FLG.dwg")
    (list "06 EL 90 FLGxMJ" "06 EL 90 FLGxMJ" "DIP-STEEL-Fitting" "0" "06 EL 90 FLGxMJ.dwg")
    (list "06 EL 90 MJ" "06 EL 90 MJ" "DIP-STEEL-Fitting" "0" "06 EL 90 MJ.dwg")
    (list "06 EL 90 UP FLG" "06 EL 90 UP FLG" "DIP-STEEL-Fitting" "0" "06 EL 90 UP FLG.dwg")
    (list "06 FCA FLG" "06 FCA FLG" "DIP-STEEL-Fitting" "0" "06 FCA FLG.dwg")
    (list "06 FLG" "06 FLG" "DIP-STEEL-Fitting" "0" "06 FLG.dwg")
    (list "06 GATE FLG" "06 GATE FLG" "DIP-STEEL-Fitting" "0" "06 GATE FLG.dwg")
    (list "06 GATE MJxFLG" "06 GATE MJxFLG" "DIP-STEEL-Fitting" "0" "06 GATE MJxFLG.dwg")
    (list "06 MJ" "06 MJ" "DIP-STEEL-Fitting" "0" "06 MJ.dwg")
    (list "06 PLUG FLG" "06 PLUG FLG" "DIP-STEEL-Fitting" "0" "06 PLUG FLG.dwg")
    (list "06 SLEEVE MJ" "06 SLEEVE MJ" "DIP-STEEL-Fitting" "0" "06 SLEEVE MJ.dwg")
    (list "06 TEE FLG" "06 TEE FLG" "DIP-STEEL-Fitting" "0" "06 TEE FLG.dwg")
    (list "06 TEE MJ" "06 TEE MJ" "DIP-STEEL-Fitting" "0" "06 TEE MJ.dwg")
    (list "06 TEE MJxMJxFLG" "06 TEE MJxMJxFLG" "DIP-STEEL-Fitting" "0" "06 TEE MJxMJxFLG.dwg")
    (list "06 TEE UP FLG" "06 TEE UP FLG" "DIP-STEEL-Fitting" "0" "06 TEE UP FLG.dwg")
    (list "0603 RED MJ" "0603 RED MJ" "DIP-STEEL-Fitting" "0" "0603 RED MJ.dwg")
    (list "0603 RED MJxFLG" "0603 RED MJxFLG" "DIP-STEEL-Fitting" "0" "0603 RED MJxFLG.dwg")
    (list "0604 EL 90 RED FLG" "0604 EL 90 RED FLG" "DIP-STEEL-Fitting" "0" "0604 EL 90 RED FLG.dwg")
    (list "0604 EL 90 RED FLG STAND" "0604 EL 90 RED FLG STAND" "DIP-STEEL-Fitting" "0" "0604 EL 90 RED FLG STAND.dwg")
    (list "0604 RED FLG" "0604 RED FLG" "DIP-STEEL-Fitting" "0" "0604 RED FLG.dwg")
    (list "0604 RED FLGxMJ" "0604 RED FLGxMJ" "DIP-STEEL-Fitting" "0" "0604 RED FLGxMJ.dwg")
    (list "0604 RED MJ" "0604 RED MJ" "DIP-STEEL-Fitting" "0" "0604 RED MJ.dwg")
    (list "0604 RED MJxFLG" "0604 RED MJxFLG" "DIP-STEEL-Fitting" "0" "0604 RED MJxFLG.dwg")
    (list "060406 TEE RED FLG" "060406 TEE RED FLG" "DIP-STEEL-Fitting" "0" "060406 TEE RED FLG.dwg")
    (list "060604 TEE FLG" "060604 TEE FLG" "DIP-STEEL-Fitting" "0" "060604 TEE FLG.dwg")
    (list "060608 TEE FLG" "060608 TEE FLG" "DIP-STEEL-Fitting" "0" "060608 TEE FLG.dwg")
    (list "08 ADP MJxFLG" "08 ADP MJxFLG" "DIP-STEEL-Fitting" "0" "08 ADP MJxFLG.dwg")
    (list "08 BTFY FLG" "08 BTFY FLG" "DIP-STEEL-Fitting" "0" "08 BTFY FLG.dwg")
    (list "08 CROSS FLG" "08 CROSS FLG" "DIP-STEEL-Fitting" "0" "08 CROSS FLG.dwg")
    (list "08 EL 11 FLG" "08 EL 11 FLG" "DIP-STEEL-Fitting" "0" "08 EL 11 FLG.dwg")
    (list "08 EL 11 FLGxMJ" "08 EL 11 FLGxMJ" "DIP-STEEL-Fitting" "0" "08 EL 11 FLGxMJ.dwg")
    (list "08 EL 11 MJ" "08 EL 11 MJ" "DIP-STEEL-Fitting" "0" "08 EL 11 MJ.dwg")
    (list "08 EL 22 DN FLG" "08 EL 22 DN FLG" "DIP-STEEL-Fitting" "0" "08 EL 22 DN FLG.dwg")
    (list "08 EL 22 FLG" "08 EL 22 FLG" "DIP-STEEL-Fitting" "0" "08 EL 22 FLG.dwg")
    (list "08 EL 22 FLGxMJ" "08 EL 22 FLGxMJ" "DIP-STEEL-Fitting" "0" "08 EL 22 FLGxMJ.dwg")
    (list "08 EL 22 MJ" "08 EL 22 MJ" "DIP-STEEL-Fitting" "0" "08 EL 22 MJ.dwg")
    (list "08 EL 22 UP FLG" "08 EL 22 UP FLG" "DIP-STEEL-Fitting" "0" "08 EL 22 UP FLG.dwg")
    (list "08 EL 45 DN FLG" "08 EL 45 DN FLG" "DIP-STEEL-Fitting" "0" "08 EL 45 DN FLG.dwg")
    (list "08 EL 45 FLG" "08 EL 45 FLG" "DIP-STEEL-Fitting" "0" "08 EL 45 FLG.dwg")
    (list "08 EL 45 FLGxMJ" "08 EL 45 FLGxMJ" "DIP-STEEL-Fitting" "0" "08 EL 45 FLGxMJ.dwg")
    (list "08 EL 45 MJ" "08 EL 45 MJ" "DIP-STEEL-Fitting" "0" "08 EL 45 MJ.dwg")
    (list "08 EL 45 UP FLG" "08 EL 45 UP FLG" "DIP-STEEL-Fitting" "0" "08 EL 45 UP FLG.dwg")
    (list "08 EL 90 DN FLG" "08 EL 90 DN FLG" "DIP-STEEL-Fitting" "0" "08 EL 90 DN FLG.dwg")
    (list "08 EL 90 FLG" "08 EL 90 FLG" "DIP-STEEL-Fitting" "0" "08 EL 90 FLG.dwg")
    (list "08 EL 90 FLGxMJ" "08 EL 90 FLGxMJ" "DIP-STEEL-Fitting" "0" "08 EL 90 FLGxMJ.dwg")
    (list "08 EL 90 MJ" "08 EL 90 MJ" "DIP-STEEL-Fitting" "0" "08 EL 90 MJ.dwg")
    (list "08 EL 90 UP FLG" "08 EL 90 UP FLG" "DIP-STEEL-Fitting" "0" "08 EL 90 UP FLG.dwg")
    (list "08 FCA FLG" "08 FCA FLG" "DIP-STEEL-Fitting" "0" "08 FCA FLG.dwg")
    (list "08 FLG" "08 FLG" "DIP-STEEL-Fitting" "0" "08 FLG.dwg")
    (list "08 GATE FLG" "08 GATE FLG" "DIP-STEEL-Fitting" "0" "08 GATE FLG.dwg")
    (list "08 GATE MJxFLG" "08 GATE MJxFLG" "DIP-STEEL-Fitting" "0" "08 GATE MJxFLG.dwg")
    (list "08 MJ" "08 MJ" "DIP-STEEL-Fitting" "0" "08 MJ.dwg")
    (list "08 PLUG FLG" "08 PLUG FLG" "DIP-STEEL-Fitting" "0" "08 PLUG FLG.dwg")
    (list "08 SLEEVE MJ" "08 SLEEVE MJ" "DIP-STEEL-Fitting" "0" "08 SLEEVE MJ.dwg")
    (list "08 TEE FLG" "08 TEE FLG" "DIP-STEEL-Fitting" "0" "08 TEE FLG.dwg")
    (list "08 TEE MJ" "08 TEE MJ" "DIP-STEEL-Fitting" "0" "08 TEE MJ.dwg")
    (list "08 TEE MJxMJxFLG" "08 TEE MJxMJxFLG" "DIP-STEEL-Fitting" "0" "08 TEE MJxMJxFLG.dwg")
    (list "08 TEE UP FLG" "08 TEE UP FLG" "DIP-STEEL-Fitting" "0" "08 TEE UP FLG.dwg")
    (list "0803 RED MJ" "0803 RED MJ" "DIP-STEEL-Fitting" "0" "0803 RED MJ.dwg")
    (list "0804 RED FLGxMJ" "0804 RED FLGxMJ" "DIP-STEEL-Fitting" "0" "0804 RED FLGxMJ.dwg")
    (list "0804 RED MJ" "0804 RED MJ" "DIP-STEEL-Fitting" "0" "0804 RED MJ.dwg")
    (list "0804 RED MJxFLG" "0804 RED MJxFLG" "DIP-STEEL-Fitting" "0" "0804 RED MJxFLG.dwg")
    (list "0806 RED FLG" "0806 RED FLG" "DIP-STEEL-Fitting" "0" "0806 RED FLG.dwg")
    (list "0806 RED FLGxMJ" "0806 RED FLGxMJ" "DIP-STEEL-Fitting" "0" "0806 RED FLGxMJ.dwg")
    (list "0806 RED MJ" "0806 RED MJ" "DIP-STEEL-Fitting" "0" "0806 RED MJ.dwg")
    (list "0806 RED MJxFLG" "0806 RED MJxFLG" "DIP-STEEL-Fitting" "0" "0806 RED MJxFLG.dwg")
    (list "080606 TEE RED FLG" "080606 TEE RED FLG" "DIP-STEEL-Fitting" "0" "080606 TEE RED FLG.dwg")
    (list "080608 TEE RED FLG" "080608 TEE RED FLG" "DIP-STEEL-Fitting" "0" "080608 TEE RED FLG.dwg")
    (list "080804 TEE FLG" "080804 TEE FLG" "DIP-STEEL-Fitting" "0" "080804 TEE FLG.dwg")
    (list "080806 TEE FLG" "080806 TEE FLG" "DIP-STEEL-Fitting" "0" "080806 TEE FLG.dwg")
    (list "10 ADP MJxFLG" "10 ADP MJxFLG" "DIP-STEEL-Fitting" "0" "10 ADP MJxFLG.dwg")
    (list "10 BTFY FLG" "10 BTFY FLG" "DIP-STEEL-Fitting" "0" "10 BTFY FLG.DWG")
    (list "10 CROSS FLG" "10 CROSS FLG" "DIP-STEEL-Fitting" "0" "10 CROSS FLG.dwg")
    (list "10 EL 11 FLG" "10 EL 11 FLG" "DIP-STEEL-Fitting" "0" "10 EL 11 FLG.dwg")
    (list "10 EL 11 FLGxMJ" "10 EL 11 FLGxMJ" "DIP-STEEL-Fitting" "0" "10 EL 11 FLGxMJ.dwg")
    (list "10 EL 11 MJ" "10 EL 11 MJ" "DIP-STEEL-Fitting" "0" "10 EL 11 MJ.dwg")
    (list "10 EL 22 DN FLG" "10 EL 22 DN FLG" "DIP-STEEL-Fitting" "0" "10 EL 22 DN FLG.dwg")
    (list "10 EL 22 FLG" "10 EL 22 FLG" "DIP-STEEL-Fitting" "0" "10 EL 22 FLG.dwg")
    (list "10 EL 22 FLGxMJ" "10 EL 22 FLGxMJ" "DIP-STEEL-Fitting" "0" "10 EL 22 FLGxMJ.dwg")
    (list "10 EL 22 MJ" "10 EL 22 MJ" "DIP-STEEL-Fitting" "0" "10 EL 22 MJ.dwg")
    (list "10 EL 22 UP FLG" "10 EL 22 UP FLG" "DIP-STEEL-Fitting" "0" "10 EL 22 UP FLG.dwg")
    (list "10 EL 45 DN FLG" "10 EL 45 DN FLG" "DIP-STEEL-Fitting" "0" "10 EL 45 DN FLG.dwg")
    (list "10 EL 45 FLG" "10 EL 45 FLG" "DIP-STEEL-Fitting" "0" "10 EL 45 FLG.dwg")
    (list "10 EL 45 FLGxMJ" "10 EL 45 FLGxMJ" "DIP-STEEL-Fitting" "0" "10 EL 45 FLGxMJ.dwg")
    (list "10 EL 45 MJ" "10 EL 45 MJ" "DIP-STEEL-Fitting" "0" "10 EL 45 MJ.dwg")
    (list "10 EL 45 UP FLG" "10 EL 45 UP FLG" "DIP-STEEL-Fitting" "0" "10 EL 45 UP FLG.dwg")
    (list "10 EL 90 DN FLG" "10 EL 90 DN FLG" "DIP-STEEL-Fitting" "0" "10 EL 90 DN FLG.dwg")
    (list "10 EL 90 FLG" "10 EL 90 FLG" "DIP-STEEL-Fitting" "0" "10 EL 90 FLG.dwg")
    (list "10 EL 90 FLGxMJ" "10 EL 90 FLGxMJ" "DIP-STEEL-Fitting" "0" "10 EL 90 FLGxMJ.dwg")
    (list "10 EL 90 MJ" "10 EL 90 MJ" "DIP-STEEL-Fitting" "0" "10 EL 90 MJ.dwg")
    (list "10 EL 90 UP FLG" "10 EL 90 UP FLG" "DIP-STEEL-Fitting" "0" "10 EL 90 UP FLG.dwg")
    (list "10 FCA FLG" "10 FCA FLG" "DIP-STEEL-Fitting" "0" "10 FCA FLG.dwg")
    (list "10 FLG" "10 FLG" "DIP-STEEL-Fitting" "0" "10 FLG.dwg")
    (list "10 GATE FLG" "10 GATE FLG" "DIP-STEEL-Fitting" "0" "10 GATE FLG.dwg")
    (list "10 GATE MJxFLG" "10 GATE MJxFLG" "DIP-STEEL-Fitting" "0" "10 GATE MJxFLG.dwg")
    (list "10 MJ" "10 MJ" "DIP-STEEL-Fitting" "0" "10 MJ.dwg")
    (list "10 PLUG FLG" "10 PLUG FLG" "DIP-STEEL-Fitting" "0" "10 PLUG FLG.dwg")
    (list "10 SLEEVE MJ" "10 SLEEVE MJ" "DIP-STEEL-Fitting" "0" "10 SLEEVE MJ.dwg")
    (list "10 TEE FLG" "10 TEE FLG" "DIP-STEEL-Fitting" "0" "10 TEE FLG.dwg")
    (list "10 TEE MJ" "10 TEE MJ" "DIP-STEEL-Fitting" "0" "10 TEE MJ.dwg")
    (list "10 TEE MJxMJxFLG" "10 TEE MJxMJxFLG" "DIP-STEEL-Fitting" "0" "10 TEE MJxMJxFLG.dwg")
    (list "10 TEE UP FLG" "10 TEE UP FLG" "DIP-STEEL-Fitting" "0" "10 TEE UP FLG.dwg")
    (list "1006 RED FLGxMJ" "1006 RED FLGxMJ" "DIP-STEEL-Fitting" "0" "1006 RED FLGxMJ.dwg")
    (list "1006 RED MJ" "1006 RED MJ" "DIP-STEEL-Fitting" "0" "1006 RED MJ.dwg")
    (list "1006 RED MJxFLG" "1006 RED MJxFLG" "DIP-STEEL-Fitting" "0" "1006 RED MJxFLG.dwg")
    (list "1008 RED FLG" "1008 RED FLG" "DIP-STEEL-Fitting" "0" "1008 RED FLG.dwg")
    (list "1008 RED FLGxMJ" "1008 RED FLGxMJ" "DIP-STEEL-Fitting" "0" "1008 RED FLGxMJ.dwg")
    (list "1008 RED MJ" "1008 RED MJ" "DIP-STEEL-Fitting" "0" "1008 RED MJ.dwg")
    (list "1008 RED MJxFLG" "1008 RED MJxFLG" "DIP-STEEL-Fitting" "0" "1008 RED MJxFLG.dwg")
    (list "101008 TEE FLG" "101008 TEE FLG" "DIP-STEEL-Fitting" "0" "101008 TEE FLG.dwg")
    (list "12 ADP MJxFLG" "12 ADP MJxFLG" "DIP-STEEL-Fitting" "0" "12 ADP MJxFLG.dwg")
    (list "12 BTFY FLG" "12 BTFY FLG" "DIP-STEEL-Fitting" "0" "12 BTFY FLG.dwg")
    (list "12 CROSS FLG" "12 CROSS FLG" "DIP-STEEL-Fitting" "0" "12 CROSS FLG.dwg")
    (list "12 EL 11 FLG" "12 EL 11 FLG" "DIP-STEEL-Fitting" "0" "12 EL 11 FLG.dwg")
    (list "12 EL 11 FLGxMJ" "12 EL 11 FLGxMJ" "DIP-STEEL-Fitting" "0" "12 EL 11 FLGxMJ.dwg")
    (list "12 EL 11 MJ" "12 EL 11 MJ" "DIP-STEEL-Fitting" "0" "12 EL 11 MJ.dwg")
    (list "12 EL 22 DN FLG" "12 EL 22 DN FLG" "DIP-STEEL-Fitting" "0" "12 EL 22 DN FLG.dwg")
    (list "12 EL 22 FLG" "12 EL 22 FLG" "DIP-STEEL-Fitting" "0" "12 EL 22 FLG.dwg")
    (list "12 EL 22 FLGxMJ" "12 EL 22 FLGxMJ" "DIP-STEEL-Fitting" "0" "12 EL 22 FLGxMJ.dwg")
    (list "12 EL 22 MJ" "12 EL 22 MJ" "DIP-STEEL-Fitting" "0" "12 EL 22 MJ.dwg")
    (list "12 EL 22 UP FLG" "12 EL 22 UP FLG" "DIP-STEEL-Fitting" "0" "12 EL 22 UP FLG.dwg")
    (list "12 EL 45 DN FLG" "12 EL 45 DN FLG" "DIP-STEEL-Fitting" "0" "12 EL 45 DN FLG.dwg")
    (list "12 EL 45 FLG" "12 EL 45 FLG" "DIP-STEEL-Fitting" "0" "12 EL 45 FLG.dwg")
    (list "12 EL 45 FLGxMJ" "12 EL 45 FLGxMJ" "DIP-STEEL-Fitting" "0" "12 EL 45 FLGxMJ.dwg")
    (list "12 EL 45 MJ" "12 EL 45 MJ" "DIP-STEEL-Fitting" "0" "12 EL 45 MJ.dwg")
    (list "12 EL 45 UP FLG" "12 EL 45 UP FLG" "DIP-STEEL-Fitting" "0" "12 EL 45 UP FLG.dwg")
    (list "12 EL 90 DN FLG" "12 EL 90 DN FLG" "DIP-STEEL-Fitting" "0" "12 EL 90 DN FLG.dwg")
    (list "12 EL 90 FLG" "12 EL 90 FLG" "DIP-STEEL-Fitting" "0" "12 EL 90 FLG.dwg")
    (list "12 EL 90 FLGxMJ" "12 EL 90 FLGxMJ" "DIP-STEEL-Fitting" "0" "12 EL 90 FLGxMJ.dwg")
    (list "12 EL 90 MJ" "12 EL 90 MJ" "DIP-STEEL-Fitting" "0" "12 EL 90 MJ.dwg")
    (list "12 EL 90 UP FLG" "12 EL 90 UP FLG" "DIP-STEEL-Fitting" "0" "12 EL 90 UP FLG.dwg")
    (list "12 FCA FLG" "12 FCA FLG" "DIP-STEEL-Fitting" "0" "12 FCA FLG.dwg")
    (list "12 FLG" "12 FLG" "DIP-STEEL-Fitting" "0" "12 FLG.dwg")
    (list "12 GATE FLG" "12 GATE FLG" "DIP-STEEL-Fitting" "0" "12 GATE FLG.dwg")
    (list "12 GATE MJxFLG" "12 GATE MJxFLG" "DIP-STEEL-Fitting" "0" "12 GATE MJxFLG.dwg")
    (list "12 MJ" "12 MJ" "DIP-STEEL-Fitting" "0" "12 MJ.dwg")
    (list "12 PLUG FLG" "12 PLUG FLG" "DIP-STEEL-Fitting" "0" "12 PLUG FLG.dwg")
    (list "12 SLEEVE MJ" "12 SLEEVE MJ" "DIP-STEEL-Fitting" "0" "12 SLEEVE MJ.dwg")
    (list "12 TEE FLG" "12 TEE FLG" "DIP-STEEL-Fitting" "0" "12 TEE FLG.dwg")
    (list "12 TEE MJ" "12 TEE MJ" "DIP-STEEL-Fitting" "0" "12 TEE MJ.dwg")
    (list "12 TEE MJxMJxFLG" "12 TEE MJxMJxFLG" "DIP-STEEL-Fitting" "0" "12 TEE MJxMJxFLG.dwg")
    (list "12 TEE UP FLG" "12 TEE UP FLG" "DIP-STEEL-Fitting" "0" "12 TEE UP FLG.dwg")
    (list "1204 RED MJ" "1204 RED MJ" "DIP-STEEL-Fitting" "0" "1204 RED MJ.dwg")
    (list "1206 EL 90 RED FLG" "1206 EL 90 RED FLG" "DIP-STEEL-Fitting" "0" "1206 EL 90 RED FLG.dwg")
    (list "1206 RED FLG" "1206 RED FLG" "DIP-STEEL-Fitting" "0" "1206 RED FLG.dwg")
    (list "1206 RED FLGxMJ" "1206 RED FLGxMJ" "DIP-STEEL-Fitting" "0" "1206 RED FLGxMJ.dwg")
    (list "1206 RED MJ" "1206 RED MJ" "DIP-STEEL-Fitting" "0" "1206 RED MJ.dwg")
    (list "1206 RED MJxFLG" "1206 RED MJxFLG" "DIP-STEEL-Fitting" "0" "1206 RED MJxFLG.dwg")
    (list "1208 EL 90 DN RED FLG" "1208 EL 90 DN RED FLG" "DIP-STEEL-Fitting" "0" "1208 EL 90 DN RED FLG.dwg")
    (list "1208 EL 90 RED FLG" "1208 EL 90 RED FLG" "DIP-STEEL-Fitting" "0" "1208 EL 90 RED FLG.dwg")
    (list "1208 RED FLG" "1208 RED FLG" "DIP-STEEL-Fitting" "0" "1208 RED FLG.dwg")
    (list "1208 RED FLGxMJ" "1208 RED FLGxMJ" "DIP-STEEL-Fitting" "0" "1208 RED FLGxMJ.dwg")
    (list "1208 RED MJ" "1208 RED MJ" "DIP-STEEL-Fitting" "0" "1208 RED MJ.dwg")
    (list "1208 RED MJxFLG" "1208 RED MJxFLG" "DIP-STEEL-Fitting" "0" "1208 RED MJxFLG.dwg")
    (list "1210 RED FLG" "1210 RED FLG" "DIP-STEEL-Fitting" "0" "1210 RED FLG.dwg")
    (list "1210 RED FLGxMJ" "1210 RED FLGxMJ" "DIP-STEEL-Fitting" "0" "1210 RED FLGxMJ.dwg")
    (list "1210 RED MJ" "1210 RED MJ" "DIP-STEEL-Fitting" "0" "1210 RED MJ.dwg")
    (list "1210 RED MJxFLG" "1210 RED MJxFLG" "DIP-STEEL-Fitting" "0" "1210 RED MJxFLG.dwg")
    (list "121206 TEE FLG" "121206 TEE FLG" "DIP-STEEL-Fitting" "0" "121206 TEE FLG.dwg")
    (list "121208 TEE FLG" "121208 TEE FLG" "DIP-STEEL-Fitting" "0" "121208 TEE FLG.dwg")
    (list "12120808 CROSS FLG" "12120808 CROSS FLG" "DIP-STEEL-Fitting" "0" "12120808 CROSS FLG.dwg")
    (list "14 EL 22 FLG" "14 EL 22 FLG" "DIP-STEEL-Fitting" "0" "14 EL 22 FLG.dwg")
    (list "14 FLG" "14 FLG" "DIP-STEEL-Fitting" "0" "14 FLG.dwg")
    (list "14 TEE FLG" "14 TEE FLG" "DIP-STEEL-Fitting" "0" "14 TEE FLG.dwg")
    (list "16 EL 90 FLG" "16 EL 90 FLG" "DIP-STEEL-Fitting" "0" "16 EL 90 FLG.dwg")
    (list "16 FCA FLG" "16 FCA FLG" "DIP-STEEL-Fitting" "0" "16 FCA FLG.dwg")
    (list "16 FLG" "16 FLG" "DIP-STEEL-Fitting" "0" "16 FLG.dwg")
    (list "18 EL 90 FLG" "18 EL 90 FLG" "DIP-STEEL-Fitting" "0" "18 EL 90 FLG.dwg")
    (list "18 FCA FLG" "18 FCA FLG" "DIP-STEEL-Fitting" "0" "18 FCA FLG.dwg")
    (list "18 FLG" "18 FLG" "DIP-STEEL-Fitting" "0" "18 FLG.dwg")
    (list "181806 TEE FLG" "181806 TEE FLG" "DIP-STEEL-Fitting" "0" "181806 TEE FLG.dwg")
    (list "20 EL 22 FLG" "20 EL 22 FLG" "DIP-STEEL-Fitting" "0" "20 EL 22 FLG.dwg")
    (list "20 EL 45 FLG" "20 EL 45 FLG" "DIP-STEEL-Fitting" "0" "20 EL 45 FLG.dwg")
    (list "20 FLG" "20 FLG" "DIP-STEEL-Fitting" "0" "20 FLG.dwg")
    (list "2014 RED FLG" "2014 RED FLG" "DIP-STEEL-Fitting" "0" "2014 RED FLG.dwg")
    (list "24 FLG" "24 FLG" "DIP-STEEL-Fitting" "0" "24 FLG.dwg")
    (list "30 EL 90 FLG" "30 EL 90 FLG" "DIP-STEEL-Fitting" "0" "30 EL 90 FLG.dwg")
    (list "30 FLG" "30 FLG" "DIP-STEEL-Fitting" "0" "30 FLG.dwg")
    ;; -- GIP-FITTING (100 blocks) --
    (list "_1 1_4 BALL GIP" "_1 1_4 BALL GIP" "GIP-Fitting" "0" "_1 1_4 BALL GIP.dwg")
    (list "_1 1_4 CAP GIP" "_1 1_4 CAP GIP" "GIP-Fitting" "0" "_1 1_4 CAP GIP.dwg")
    (list "_1 1_4 COUPLING GIP" "_1 1_4 COUPLING GIP" "GIP-Fitting" "0" "_1 1_4 COUPLING GIP.dwg")
    (list "_1 1_4 EL 45 DN GIP" "_1 1_4 EL 45 DN GIP" "GIP-Fitting" "0" "_1 1_4 EL 45 DN GIP.dwg")
    (list "_1 1_4 EL 45 GIP" "_1 1_4 EL 45 GIP" "GIP-Fitting" "0" "_1 1_4 EL 45 GIP.dwg")
    (list "_1 1_4 EL 45 UP GIP" "_1 1_4 EL 45 UP GIP" "GIP-Fitting" "0" "_1 1_4 EL 45 UP GIP.dwg")
    (list "_1 1_4 EL 90 DN GIP" "_1 1_4 EL 90 DN GIP" "GIP-Fitting" "0" "_1 1_4 EL 90 DN GIP.dwg")
    (list "_1 1_4 EL 90 GIP" "_1 1_4 EL 90 GIP" "GIP-Fitting" "0" "_1 1_4 EL 90 GIP.dwg")
    (list "_1 1_4 EL 90 UP GIP" "_1 1_4 EL 90 UP GIP" "GIP-Fitting" "0" "_1 1_4 EL 90 UP GIP.dwg")
    (list "_1 1_4 GATE DIP" "_1 1_4 GATE DIP" "GIP-Fitting" "0" "_1 1_4 GATE DIP.dwg")
    (list "_1 1_4 NIPPLE GIP" "_1 1_4 NIPPLE GIP" "GIP-Fitting" "0" "_1 1_4 NIPPLE GIP.dwg")
    (list "_1 1_4 PLUG GIP" "_1 1_4 PLUG GIP" "GIP-Fitting" "0" "_1 1_4 PLUG GIP.dwg")
    (list "_1 1_4 TEE DN GIP" "_1 1_4 TEE DN GIP" "GIP-Fitting" "0" "_1 1_4 TEE DN GIP.dwg")
    (list "_1 1_4 TEE GIP" "_1 1_4 TEE GIP" "GIP-Fitting" "0" "_1 1_4 TEE GIP.dwg")
    (list "_1 1_4 TEE UP GIP" "_1 1_4 TEE UP GIP" "GIP-Fitting" "0" "_1 1_4 TEE UP GIP.dwg")
    (list "_1 1_4 UNION GIP" "_1 1_4 UNION GIP" "GIP-Fitting" "0" "_1 1_4 UNION GIP.dwg")
    (list "_1 1_2 BALL GIP" "_1 1_2 BALL GIP" "GIP-Fitting" "0" "_1 1_2 BALL GIP.dwg")
    (list "_1 1_2 CAP GIP" "_1 1_2 CAP GIP" "GIP-Fitting" "0" "_1 1_2 CAP GIP.dwg")
    (list "_1 1_2 COUPLING GIP" "_1 1_2 COUPLING GIP" "GIP-Fitting" "0" "_1 1_2 COUPLING GIP.dwg")
    (list "_1 1_2 EL 45 DN GIP" "_1 1_2 EL 45 DN GIP" "GIP-Fitting" "0" "_1 1_2 EL 45 DN GIP.dwg")
    (list "_1 1_2 EL 45 GIP" "_1 1_2 EL 45 GIP" "GIP-Fitting" "0" "_1 1_2 EL 45 GIP.dwg")
    (list "_1 1_2 EL 45 UP GIP" "_1 1_2 EL 45 UP GIP" "GIP-Fitting" "0" "_1 1_2 EL 45 UP GIP.dwg")
    (list "_1 1_2 EL 90 DN GIP" "_1 1_2 EL 90 DN GIP" "GIP-Fitting" "0" "_1 1_2 EL 90 DN GIP.dwg")
    (list "_1 1_2 EL 90 GIP" "_1 1_2 EL 90 GIP" "GIP-Fitting" "0" "_1 1_2 EL 90 GIP.dwg")
    (list "_1 1_2 EL 90 UP GIP" "_1 1_2 EL 90 UP GIP" "GIP-Fitting" "0" "_1 1_2 EL 90 UP GIP.dwg")
    (list "_1 1_2 GATE GIP" "_1 1_2 GATE GIP" "GIP-Fitting" "0" "_1 1_2 GATE GIP.dwg")
    (list "_1 1_2 NIPPLE GIP" "_1 1_2 NIPPLE GIP" "GIP-Fitting" "0" "_1 1_2 NIPPLE GIP.dwg")
    (list "_1 1_2 PLUG GIP" "_1 1_2 PLUG GIP" "GIP-Fitting" "0" "_1 1_2 PLUG GIP.dwg")
    (list "_1 1_2 TEE DN GIP" "_1 1_2 TEE DN GIP" "GIP-Fitting" "0" "_1 1_2 TEE DN GIP.dwg")
    (list "_1 1_2 TEE GIP" "_1 1_2 TEE GIP" "GIP-Fitting" "0" "_1 1_2 TEE GIP.dwg")
    (list "_1 1_2 TEE UP GIP" "_1 1_2 TEE UP GIP" "GIP-Fitting" "0" "_1 1_2 TEE UP GIP.dwg")
    (list "_1 1_2 UNION GIP" "_1 1_2 UNION GIP" "GIP-Fitting" "0" "_1 1_2 UNION GIP.dwg")
    (list "_3_4 BALL GIP" "_3_4 BALL GIP" "GIP-Fitting" "0" "_3_4 BALL GIP.dwg")
    (list "_3_4 CAP GIP" "_3_4 CAP GIP" "GIP-Fitting" "0" "_3_4 CAP GIP.dwg")
    (list "_3_4 COUPLING GIP" "_3_4 COUPLING GIP" "GIP-Fitting" "0" "_3_4 COUPLING GIP.dwg")
    (list "_3_4 EL 45 DN GIP" "_3_4 EL 45 DN GIP" "GIP-Fitting" "0" "_3_4 EL 45 DN GIP.dwg")
    (list "_3_4 EL 45 GIP" "_3_4 EL 45 GIP" "GIP-Fitting" "0" "_3_4 EL 45 GIP.dwg")
    (list "_3_4 EL 45 UP GIP" "_3_4 EL 45 UP GIP" "GIP-Fitting" "0" "_3_4 EL 45 UP GIP.dwg")
    (list "_3_4 EL 90 DN GIP" "_3_4 EL 90 DN GIP" "GIP-Fitting" "0" "_3_4 EL 90 DN GIP.dwg")
    (list "_3_4 EL 90 GIP" "_3_4 EL 90 GIP" "GIP-Fitting" "0" "_3_4 EL 90 GIP.dwg")
    (list "_3_4 EL 90 UP GIP" "_3_4 EL 90 UP GIP" "GIP-Fitting" "0" "_3_4 EL 90 UP GIP.dwg")
    (list "_3_4 GATE GIP" "_3_4 GATE GIP" "GIP-Fitting" "0" "_3_4 GATE GIP.dwg")
    (list "_3_4 HOSE BIBB GIP" "_3_4 HOSE BIBB GIP" "GIP-Fitting" "0" "_3_4 HOSE BIBB GIP.dwg")
    (list "_3_4 NIPPLE GIP" "_3_4 NIPPLE GIP" "GIP-Fitting" "0" "_3_4 NIPPLE GIP.dwg")
    (list "_3_4 PLUG GIP" "_3_4 PLUG GIP" "GIP-Fitting" "0" "_3_4 PLUG GIP.dwg")
    (list "_3_4 TEE DN GIP" "_3_4 TEE DN GIP" "GIP-Fitting" "0" "_3_4 TEE DN GIP.dwg")
    (list "_3_4 TEE GIP" "_3_4 TEE GIP" "GIP-Fitting" "0" "_3_4 TEE GIP.dwg")
    (list "_3_4 TEE UP GIP" "_3_4 TEE UP GIP" "GIP-Fitting" "0" "_3_4 TEE UP GIP.dwg")
    (list "_3_4 UNION GIP" "_3_4 UNION GIP" "GIP-Fitting" "0" "_3_4 UNION GIP.dwg")
    (list "01 BALL GIP" "01 BALL GIP" "GIP-Fitting" "0" "01 BALL GIP.dwg")
    (list "01 CAP GIP" "01 CAP GIP" "GIP-Fitting" "0" "01 CAP GIP.dwg")
    (list "01 COUPLING GIP" "01 COUPLING GIP" "GIP-Fitting" "0" "01 COUPLING GIP.dwg")
    (list "01 EL 45 DN GIP" "01 EL 45 DN GIP" "GIP-Fitting" "0" "01 EL 45 DN GIP.dwg")
    (list "01 EL 45 GIP" "01 EL 45 GIP" "GIP-Fitting" "0" "01 EL 45 GIP.dwg")
    (list "01 EL 45 UP GIP" "01 EL 45 UP GIP" "GIP-Fitting" "0" "01 EL 45 UP GIP.dwg")
    (list "01 EL 90 DN GIP" "01 EL 90 DN GIP" "GIP-Fitting" "0" "01 EL 90 DN GIP.dwg")
    (list "01 EL 90 GIP" "01 EL 90 GIP" "GIP-Fitting" "0" "01 EL 90 GIP.dwg")
    (list "01 EL 90 UP GIP" "01 EL 90 UP GIP" "GIP-Fitting" "0" "01 EL 90 UP GIP.dwg")
    (list "01 GATE GIP" "01 GATE GIP" "GIP-Fitting" "0" "01 GATE GIP.dwg")
    (list "01 NIPPLE GIP" "01 NIPPLE GIP" "GIP-Fitting" "0" "01 NIPPLE GIP.dwg")
    (list "01 PLUG GIP" "01 PLUG GIP" "GIP-Fitting" "0" "01 PLUG GIP.dwg")
    (list "01 TEE DN GIP" "01 TEE DN GIP" "GIP-Fitting" "0" "01 TEE DN GIP.dwg")
    (list "01 TEE GIP" "01 TEE GIP" "GIP-Fitting" "0" "01 TEE GIP.dwg")
    (list "01 TEE UP GIP" "01 TEE UP GIP" "GIP-Fitting" "0" "01 TEE UP GIP.dwg")
    (list "01 UNION GIP" "01 UNION GIP" "GIP-Fitting" "0" "01 UNION GIP.dwg")
    (list "02 BALL GIP" "02 BALL GIP" "GIP-Fitting" "0" "02 BALL GIP.dwg")
    (list "02 CAP GIP" "02 CAP GIP" "GIP-Fitting" "0" "02 CAP GIP.dwg")
    (list "02 COUPLING GIP" "02 COUPLING GIP" "GIP-Fitting" "0" "02 COUPLING GIP.dwg")
    (list "02 EL 45 DN GIP" "02 EL 45 DN GIP" "GIP-Fitting" "0" "02 EL 45 DN GIP.dwg")
    (list "02 EL 45 GIP" "02 EL 45 GIP" "GIP-Fitting" "0" "02 EL 45 GIP.dwg")
    (list "02 EL 45 UP GIP" "02 EL 45 UP GIP" "GIP-Fitting" "0" "02 EL 45 UP GIP.dwg")
    (list "02 EL 90 DN GIP" "02 EL 90 DN GIP" "GIP-Fitting" "0" "02 EL 90 DN GIP.dwg")
    (list "02 EL 90 GIP" "02 EL 90 GIP" "GIP-Fitting" "0" "02 EL 90 GIP.dwg")
    (list "02 EL 90 UP GIP" "02 EL 90 UP GIP" "GIP-Fitting" "0" "02 EL 90 UP GIP.dwg")
    (list "02 GATE GIP" "02 GATE GIP" "GIP-Fitting" "0" "02 GATE GIP.dwg")
    (list "02 NIPPLE GIP" "02 NIPPLE GIP" "GIP-Fitting" "0" "02 NIPPLE GIP.dwg")
    (list "02 PLUG GIP" "02 PLUG GIP" "GIP-Fitting" "0" "02 PLUG GIP.dwg")
    (list "02 TEE DN GIP" "02 TEE DN GIP" "GIP-Fitting" "0" "02 TEE DN GIP.dwg")
    (list "02 TEE GIP" "02 TEE GIP" "GIP-Fitting" "0" "02 TEE GIP.dwg")
    (list "02 TEE UP GIP" "02 TEE UP GIP" "GIP-Fitting" "0" "02 TEE UP GIP.dwg")
    (list "02 UNION GIP" "02 UNION GIP" "GIP-Fitting" "0" "02 UNION GIP.dwg")
    (list "03 BALL GIP" "03 BALL GIP" "GIP-Fitting" "0" "03 BALL GIP.dwg")
    (list "03 CAP GIP" "03 CAP GIP" "GIP-Fitting" "0" "03 CAP GIP.dwg")
    (list "03 COUPLING GIP" "03 COUPLING GIP" "GIP-Fitting" "0" "03 COUPLING GIP.dwg")
    (list "03 EL 45 DN GIP" "03 EL 45 DN GIP" "GIP-Fitting" "0" "03 EL 45 DN GIP.dwg")
    (list "03 EL 45 GIP" "03 EL 45 GIP" "GIP-Fitting" "0" "03 EL 45 GIP.dwg")
    (list "03 EL 45 UP GIP" "03 EL 45 UP GIP" "GIP-Fitting" "0" "03 EL 45 UP GIP.dwg")
    (list "03 EL 90 DN GIP" "03 EL 90 DN GIP" "GIP-Fitting" "0" "03 EL 90 DN GIP.dwg")
    (list "03 EL 90 GIP" "03 EL 90 GIP" "GIP-Fitting" "0" "03 EL 90 GIP.dwg")
    (list "03 EL 90 UP GIP" "03 EL 90 UP GIP" "GIP-Fitting" "0" "03 EL 90 UP GIP.dwg")
    (list "03 GATE GIP" "03 GATE GIP" "GIP-Fitting" "0" "03 GATE GIP.dwg")
    (list "03 NIPPLE GIP" "03 NIPPLE GIP" "GIP-Fitting" "0" "03 NIPPLE GIP.dwg")
    (list "03 PLUG GIP" "03 PLUG GIP" "GIP-Fitting" "0" "03 PLUG GIP.dwg")
    (list "03 TEE DN GIP" "03 TEE DN GIP" "GIP-Fitting" "0" "03 TEE DN GIP.dwg")
    (list "03 TEE GIP" "03 TEE GIP" "GIP-Fitting" "0" "03 TEE GIP.dwg")
    (list "03 TEE UP GIP" "03 TEE UP GIP" "GIP-Fitting" "0" "03 TEE UP GIP.dwg")
    (list "03 UNION GIP" "03 UNION GIP" "GIP-Fitting" "0" "03 UNION GIP.dwg")
    (list "04 EL 90 GIP" "04 EL 90 GIP" "GIP-Fitting" "0" "04 EL 90 GIP.dwg")
    (list "04 NIPPLE GIP" "04 NIPPLE GIP" "GIP-Fitting" "0" "04 NIPPLE GIP.dwg")
    (list "04 TEE GIP" "04 TEE GIP" "GIP-Fitting" "0" "04 TEE GIP.dwg")
    ;; -- LOGOS (5 blocks) --
    (list "B&R Logo" "LOGO BR1" "Logos" "0" "LOGO BR1.dwg")
    (list "B&R Logo" "LOGO BR2" "Logos" "0" "LOGO BR2.dwg")
    (list "Santa Rosa" "LOGO CITY OF SANTA ROSA" "Logos" "0" "LOGO CITY OF SANTA ROSA.dwg")
    (list "Sonoma County" "LOGO COUNTY SEAL" "Logos" "0" "LOGO COUNTY SEAL.dwg")
    (list "Town Of Windsor" "LOGO TOW" "Logos" "0" "LOGO TOW.dwg")
    ;; -- MISC-1 (79 blocks) --
    (list "Layers - Detail - Piping/Schematics Only" "$BR Prot-detail" "Misc-1" "0" "$BR Prot-detail.dwg")
    (list "Layers - Existing" "$BR PROT-existing" "Misc-1" "0" "$BR PROT-existing.dwg")
    (list "Layers - New" "$BR PROT-new" "Misc-1" "0" "$BR PROT-new.dwg")
    (list "00 Pipe Break" "00 PIPE BREAK" "Misc-1" "0" "00 PIPE BREAK.dwg")
    (list "Break" "BREAK" "Misc-1" "0" "BREAK.dwg")
    (list "Crows Feet" "CROWS FEET" "Misc-1" "0" "CROWS FEET.dwg")
    (list "Line Label" "LABEL LINE" "Misc-1" "0" "LABEL LINE.dwg")
    (list "Slope Symbol" "SLOPE" "Misc-1" "0" "SLOPE.DWG")
    (list "Sheet Tag" "SHEET TAG" "Misc-1" "0" "SHEET TAG.dwg")
    (list "Tik" "TIK" "Misc-1" "0" "TIK.DWG")
    (list "Wiggle" "WIGGLE" "Misc-1" "0" "WIGGLE.dwg")
    (list "Project Site Arrow" "ARR PROJECT" "Misc-1" "0" "ARR PROJECT.dwg")
    (list "Star" "STAR" "Misc-1" "0" "STAR.dwg")
    (list "Circle-Hexagon-Oval-Pentagon-Square" "CIRCLE HEX SQUARE PENTAGON" "Misc-1" "0" "CIRCLE HEX SQUARE PENTAGON.dwg")
    (list "Revision Triangle - MS" "REVISION" "Misc-1" "0" "REVISION.dwg")
    (list "North Arrow - Standard" "NORTHA2" "Misc-1" "0" "NORTHA2.DWG")
    (list "Scale - Standard" "SCALE" "Misc-1" "0" "SCALE.DWG")
    (list "North Arrow - Fancy - MS" "NORTH FANCY" "Misc-1" "0" "NORTH FANCY.dwg")
    (list "North Arrow - Fancy - PS" "NORTH FANCY" "Misc-1" "0" "NORTH FANCY.dwg")
    (list "North Arrow - Smaller - Use For 11x17's" "NORTHA2" "Misc-1" "0" "NORTHA2.DWG")
    (list "Scale - Smaller - Use For 11x17's" "SCALE2" "Misc-1" "0" "J:\\LIB\\ACAD-custom\\lib\\SCALE2.DWG")
    (list "Tree - Save" "TREE SAVE" "Misc-1" "0" "TREE SAVE.dwg")
    (list "Tree - Remove" "TREE REMOVE" "Misc-1" "0" "TREE REMOVE.dwg")
    (list "Section" "SECTION STRAIGHT" "Misc-1" "0" "SECTION STRAIGHT.dwg")
    (list "Section With Angle" "SECTION ANGLED" "Misc-1" "0" "SECTION ANGLED.dwg")
    (list "Detail/Section Bubble" "SECTION BUBBLE" "Misc-1" "0" "SECTION BUBBLE.dwg")
    (list "Hydro Bubble" "HYDRO  BUBBLE" "Misc-1" "0" "HYDRO  BUBBLE.dwg")
    (list "Elevation Bubble" "ELEVATION BUBBLE" "Misc-1" "0" "ELEVATION BUBBLE.dwg")
    (list "Sheet Note Title - Demolition" "NOTE SHEET SETUP TITLE" "Misc-1" "0" "NOTE SHEET SETUP TITLE.dwg")
    (list "Sheet Note Setup - Demolition" "NOTE SHEET SETUP DEMOLITION" "Misc-1" "0" "NOTE SHEET SETUP DEMOLITION.dwg")
    (list "Legend - Demolition" "LEGEND DEMOLITION" "Misc-1" "0" "LEGEND DEMOLITION.dwg")
    (list "Sheet Note Title" "NOTE SHEET SETUP TITLE" "Misc-1" "0" "NOTE SHEET SETUP TITLE.dwg")
    (list "Sheet Note Setup - Insert in MS" "NOTE SHEET SETUP" "Misc-1" "0" "NOTE SHEET SETUP.dwg")
    (list "Sheet Note Setup - Piping - Insert in MS" "NOTE SHEET SETUP PIPING" "Misc-1" "0" "NOTE SHEET SETUP PIPING.dwg")
    (list "Sheet Note Setup - Oval" "NOTE SHEET SETUP OVAL" "Misc-1" "0" "NOTE SHEET SETUP OVAL.dwg")
    (list "Sheet Note Setup - Square" "NOTE SHEET SETUP SQUARE" "Misc-1" "0" "NOTE SHEET SETUP SQUARE.dwg")
    (list "Note Setup - MText Setup" "NOTE SETUP" "Misc-1" "0" "NOTE SETUP.dwg")
    (list "Note - Underground Utility Information Provided by Others" "NOTE UTILITY BY OTHERS" "Misc-1" "0" "NOTE UTILITY BY OTHERS.dwg")
    (list "Note - Storm Drain - Place Under Coordinate Table" "NOTE SD" "Misc-1" "0" "NOTE SD.dwg")
    (list "Legend - AutoTurn" "LEGEND AUTOTURN" "Misc-1" "0" "LEGEND AUTOTURN.dwg")
    (list "Legend - Curb Types" "LEGEND CURB" "Misc-1" "0" "LEGEND CURB.dwg")
    (list "Legend - Earthwork Cut/Fill Table" "LEGEND EARTHWORK" "Misc-1" "0" "LEGEND EARTHWORK.dwg")
    (list "Legend - Hydrology" "HYDROLOGY LEGEND" "Misc-1" "0" "J:\\LIB\\BR\\$ - Legend - Hydrology.dwg")
    (list "Legend - Pavement Structural Table" "LEGEND PAVEMENT" "Misc-1" "0" "LEGEND PAVEMENT.dwg")
    (list "Legend - Piping Table - L140R" "LEGEND PIPE" "Misc-1" "0" "LEGEND PIPE.dwg")
    (list "Legend - Piping Table - L200B" "LEGEND PIPE" "Misc-1" "0" "LEGEND PIPE.dwg")
    (list "Legend - Section & Details" "LEGEND SYMBOLS" "Misc-1" "0" "LEGEND SYMBOLS.dwg")
    (list "Legend - Setup - Half Size" "LEGEND SETUP HALF" "Misc-1" "0" "LEGEND SETUP HALF.dwg")
    (list "Legend - Setup - Full Size" "LEGEND SETUP FULL" "Misc-1" "0" "LEGEND SETUP FULL.dwg")
    (list "Stamp - DRAFT" "STAMP DRAFT" "Misc-1" "0" "STAMP DRAFT.dwg")
    (list "Stamp - Add Text" "STAMP TEXT BOX" "Misc-1" "0" "STAMP TEXT BOX.dwg")
    (list "Stamp - __% Submittal" "STAMP SUBMIT" "Misc-1" "0" "STAMP SUBMIT.dwg")
    (list "Stamp-Preliminary - Not For Construction" "STAMP NOT FOR CONSTRUCTION" "Misc-1" "0" "STAMP NOT FOR CONSTRUCTION.dwg")
    (list "Stamp-Preliminary - For Study Purposes Only" "STAMP PRELIMINARY" "Misc-1" "0" "STAMP PRELIMINARY.DWG")
    (list "Stamp - Record Drawing" "STAMP RECORD DRAWING" "Misc-1" "0" "STAMP RECORD DRAWING.dwg")
    (list "Stamp - This Drawing Reduced Approximately Half Size" "STAMP HALFSIZE" "Misc-1" "0" "STAMP HALFSIZE.dwg")
    (list "Stamp - Pothole - Storm Drain" "STAMP POTHOLE SD" "Misc-1" "0" "STAMP POTHOLE SD.dwg")
    (list "Stamp - Sheet Will Be Prepared Durning the Construction Document Phase of the Project" "STAMP SHEET COMPLETE CONSTRUCTION PHASE" "Misc-1" "0" "STAMP SHEET COMPLETE CONSTRUCTION PHASE.dwg")
    (list "Title - Exhibit - Half Size" "TB EXHIBIT TITLE HALF" "Misc-1" "0" "TB EXHIBIT TITLE HALF.dwg")
    (list "Title - Exhibit - Full Size" "TB EXHIBIT TITLE FULL" "Misc-1" "0" "TB EXHIBIT TITLE FULL.dwg")
    (list "Title - Detail/Section With Bubble/Without Bubble - \"Not To Scale\"" "TITLE DETAIL" "Misc-1" "0" "TITLE DETAIL.dwg")
    (list "Title - Section With Bubble/Without Bubble - Fill In Horz & Vert Scales" "TITLE SECTION1" "Misc-1" "0" "TITLE SECTION1.dwg")
    (list "Title - Plan - Use on Plan & Profile Sheets" "TITLE PLAN PROFILE" "Misc-1" "0" "TITLE PLAN PROFILE.DWG")
    (list "Title - Profile - Fill In Horz & Vert Scales" "TITLE PLAN PROFILE" "Misc-1" "0" "TITLE PLAN PROFILE.DWG")
    (list "CL" "CL" "Misc-1" "0" "CL.DWG")
    (list "FL" "FL" "Misc-1" "0" "FL.DWG")
    (list "PL" "PL" "Misc-1" "0" "PL.DWG")
    (list "Rock Pieces" "ROCK" "Misc-1" "0" "ROCK.dwg")
    (list "Rock Pieces With Stretch" "ROCK WITH STRETCH" "Misc-1" "0" "ROCK WITH STRETCH.dwg")
    (list "Square - Use For Barricades" "SQUARE" "Misc-1" "0" "SQUARE.dwg")
    (list "Circle - Filled" "CIRCLE SQUARE" "Misc-1" "0" "CIRCLE SQUARE.DWG")
    (list "Square - Filled" "CIRCLE SQUARE" "Misc-1" "0" "CIRCLE SQUARE.DWG")
    (list "Scale - 0' To 500'" "SCALE FEET" "Misc-1" "0" "SCALE FEET.dwg")
    (list "Scale - 0 Mile To 1/4 Mile" "SCALE MILE" "Misc-1" "0" "SCALE MILE.dwg")
    (list "Stamp - Basis of Bearing & Benchmark" "STAMP SVY BOB BM" "Misc-1" "0" "STAMP SVY BOB BM.DWG")
    (list "00 Pipe Section" "00 PIPE SECTION" "Misc-1" "0" "00 PIPE SECTION.dwg")
    (list "Revision Triangle - PS" "REVISION" "Misc-1" "0" "REVISION.dwg")
    (list "Sheet Note Setup - Square - Use for Multi Sheets" "NOTE SHEET SETUP SQUARE - MODIFIED" "Misc-1" "0" "NOTE SHEET SETUP SQUARE - MODIFIED.dwg")
    (list "Note Setup - Property Line Note & MText Setup" "NOTE SETUP-PROPERTY LINE AND GENERAL SHEET NOTES" "Misc-1" "0" "NOTE SETUP-PROPERTY LINE AND GENERAL SHEET NOTES.dwg")
    ;; -- MISC-2 (13 blocks) --
    (list "Project Site Arrow" "ARR PROJECT" "Misc-2" "0" "ARR PROJECT.dwg")
    (list "Star" "STAR" "Misc-2" "0" "STAR.dwg")
    (list "Creek Name" "TEXT CREEK NAME" "Misc-2" "0" "TEXT CREEK NAME.dwg")
    (list "Street Name" "TEXT STREET NAME" "Misc-2" "0" "TEXT STREET NAME.dwg")
    (list "Limit of Work" "TEXT LIMIT OF WORK" "Misc-2" "0" "TEXT LIMIT OF WORK.dwg")
    (list "Building Name" "TEXT BUILDING NAME" "Misc-2" "0" "TEXT BUILDING NAME.dwg")
    (list "Finished Floor Elevation" "TEXT FINISHED FLOOR" "Misc-2" "0" "TEXT FINISHED FLOOR.dwg")
    (list "Pad Elevation" "TEXT PAD" "Misc-2" "0" "TEXT PAD.dwg")
    (list "Building Name/Finished Floor Elevation/Pad Elevation" "TEXT BUILDING FINISHED FLOOR PAD" "Misc-2" "0" "TEXT BUILDING FINISHED FLOOR PAD.dwg")
    (list "Sheet Continuation" "SHEET TAG CONTINUATION" "Misc-2" "0" "SHEET TAG CONTINUATION.DWG")
    (list "Sheet Matchline - Left" "SHEET TAG MATCHLINE LEFT" "Misc-2" "0" "SHEET TAG MATCHLINE LEFT.dwg")
    (list "Sheet Matchline - Right" "SHEET TAG MATCHLINE RIGHT" "Misc-2" "0" "SHEET TAG MATCHLINE RIGHT.dwg")
    (list "Sheet Key Map" "SETUP KEY MAP" "Misc-2" "0" "SETUP KEY MAP.dwg")
    ;; -- MISC-3 (32 blocks) --
    (list "N&E Coordinate Marker with dot" "SVY N&E COORDS" "Misc-3" "0" "SVY N&E COORDS.dwg")
    (list "N&E Coordinate Marker with leader" "SVY N&E COORDS with leader" "Misc-3" "0" "SVY N&E COORDS with leader.DWG")
    (list "Building Grid Layout" "LAYOUT BUILDING GRID" "Misc-3" "0" "LAYOUT BUILDING GRID.dwg")
    (list "Abbreviations" "ABBREVIATIONS LIST" "Misc-3" "0" "J:\\LIB\\BR\\$ - Abbreviations.dwg")
    (list "Legend - Earthwork Cut/Fill Table" "LEGEND EARTHWORK" "Misc-3" "0" "LEGEND EARTHWORK.dwg")
    (list "Legend - Standard" "LEGEND" "Misc-3" "0" "J:\\LIB\\BR\\$ - Legend - Basic.dwg")
    (list "Legend - Symbols" "LEGEND-SYMBOLS" "Misc-3" "0" "J:\\LIB\\BR\\$ - Legend - Symbols.dwg")
    (list "Note - List of Codes & Standards" "LIST OF CODES AND STANDARDS" "Misc-3" "0" "J:\\LIB\\BR\\$ - Notes - List of Codes & Standards.dwg")
    (list "Note - Fire Protection - 1" "NOTES-FIRE PROTECTION NOTES - 1" "Misc-3" "0" "J:\\LIB\\BR\\$ - Notes - Fire Protection Notes - Compilation.dwg")
    (list "Note - Fire Protection - 2" "NOTES-FIRE PROTECTION NOTES - 2" "Misc-3" "0" "J:\\LIB\\BR\\$ - Notes - Fire Protection Notes - Compilation.dwg")
    (list "Pavement Marking - ADA" "PAINT HC" "Misc-3" "0" "PAINT HC.dwg")
    (list "Pavement Marking - EV" "PAINT ELEC CHARGE" "Misc-3" "0" "PAINT ELEC CHARGE.dwg")
    (list "Compact" "PAINT COMPACT" "Misc-3" "0" "PAINT COMPACT.dwg")
    (list "Tree - Save" "TREE SAVE" "Misc-3" "0" "TREE SAVE.dwg")
    (list "Tree - Remove" "TREE REMOVE" "Misc-3" "0" "TREE REMOVE.dwg")
    (list "Sheet Note Title - Demolition" "NOTE SHEET SETUP TITLE" "Misc-3" "0" "NOTE SHEET SETUP TITLE.dwg")
    (list "Sheet Note Setup - Demolition" "NOTE SHEET SETUP DEMOLITION" "Misc-3" "0" "NOTE SHEET SETUP DEMOLITION.dwg")
    (list "Legend - Demolition" "LEGEND DEMOLITION" "Misc-3" "0" "LEGEND DEMOLITION.dwg")
    (list "Sheet Note Title - Grading" "NOTE SHEET SETUP TITLE" "Misc-3" "0" "NOTE SHEET SETUP TITLE.dwg")
    (list "Legend - Curb Types" "LEGEND CURB" "Misc-3" "0" "LEGEND CURB.dwg")
    (list "Sheet Note Title - Utility" "NOTE SHEET SETUP TITLE" "Misc-3" "0" "NOTE SHEET SETUP TITLE.dwg")
    (list "Legend - Pavement Structural Table" "LEGEND PAVEMENT" "Misc-3" "0" "LEGEND PAVEMENT.dwg")
    (list "Legend - Erosion" "LEGEND-EROSION" "Misc-3" "0" "J:\\LIB\\BR\\Erosion - Compilation.dwg")
    (list "Inlet Protection - 18\" or Larger" "EROSION PROTECT1" "Misc-3" "0" "EROSION PROTECT1.dwg")
    (list "Inlet Protection - Smaller than 18\"" "EROSION PROTECT2" "Misc-3" "0" "EROSION PROTECT2.dwg")
    (list "Fiber Roll Swale Check" "EROSION CHECK" "Misc-3" "0" "EROSION CHECK.dwg")
    (list "Fiber Roll Swale Check" "EROSION CHECK" "Misc-3" "0" "EROSION CHECK.dwg")
    (list "Catch Basin Protection - True Dam" "EROSION TRUEDAM" "Misc-3" "0" "EROSION TRUEDAM.dwg")
    (list "Note - Water Pollution Control" "NOTE-WATER POLLUTION CONTROL" "Misc-3" "0" "J:\\LIB\\BR\\$ - Legend & Notes - Water Pollution Control - Compilation.dwg")
    (list "Legend - Water Pollution Control" "LEGEND-WATER POLLUTION CONTROL" "Misc-3" "0" "J:\\LIB\\BR\\$ - Legend & Notes - Water Pollution Control - Compilation.dwg")
    (list "Legend & Note - Water Pollution Control" "LEGEND-NOTE-WATER POLLUTION CONTROL" "Misc-3" "0" "J:\\LIB\\BR\\$ - Legend & Notes - Water Pollution Control - Compilation.dwg")
    (list "Legend - Hydrology" "HYDROLOGY LEGEND" "Misc-3" "0" "J:\\LIB\\BR\\$ - Legend - Hydrology.dwg")
    ;; -- PVC-FITTING (104 blocks) --
    (list "03 UNION PVC" "03 UNION PVC" "PVC-Fitting" "0" "03 UNION PVC.dwg")
    (list "_1 1_2 01 RED PVC" "_1 1_2 01 RED PVC" "PVC-Fitting" "0" "_1 1_2 01 RED PVC.dwg")
    (list "_1 1_2 1_2 RED PVC" "_1 1_2 1_2 RED PVC" "PVC-Fitting" "0" "_1 1_2 1_2 RED PVC.dwg")
    (list "_1 1_2 3_4 RED PVC" "_1 1_2 3_4 RED PVC" "PVC-Fitting" "0" "_1 1_2 3_4 RED PVC.dwg")
    (list "_1 1_2 ADP SXM PVC" "_1 1_2 ADP SXM PVC" "PVC-Fitting" "0" "_1 1_2 ADP SXM PVC.dwg")
    (list "_1 1_2 BALL PVC" "_1 1_2 BALL PVC" "PVC-Fitting" "0" "_1 1_2 BALL PVC.dwg")
    (list "_1 1_2 CAP PVC" "_1 1_2 CAP PVC" "PVC-Fitting" "0" "_1 1_2 CAP PVC.dwg")
    (list "_1 1_2 COUPLING PVC" "_1 1_2 COUPLING PVC" "PVC-Fitting" "0" "_1 1_2 COUPLING PVC.dwg")
    (list "_1 1_2 CROSS PVC" "_1 1_2 CROSS PVC" "PVC-Fitting" "0" "_1 1_2 CROSS PVC.dwg")
    (list "_1 1_2 EL 22 DN PVC" "_1 1_2 EL 22 DN PVC" "PVC-Fitting" "0" "_1 1_2 EL 22 DN PVC.dwg")
    (list "_1 1_2 EL 22 PVC" "_1 1_2 EL 22 PVC" "PVC-Fitting" "0" "_1 1_2 EL 22 PVC.dwg")
    (list "_1 1_2 EL 22 UP PVC" "_1 1_2 EL 22 UP PVC" "PVC-Fitting" "0" "_1 1_2 EL 22 UP PVC.dwg")
    (list "_1 1_2 EL 45 DN PVC" "_1 1_2 EL 45 DN PVC" "PVC-Fitting" "0" "_1 1_2 EL 45 DN PVC.dwg")
    (list "_1 1_2 EL 45 PVC" "_1 1_2 EL 45 PVC" "PVC-Fitting" "0" "_1 1_2 EL 45 PVC.dwg")
    (list "_1 1_2 EL 45 UP PVC" "_1 1_2 EL 45 UP PVC" "PVC-Fitting" "0" "_1 1_2 EL 45 UP PVC.dwg")
    (list "_1 1_2 EL 90 DN PVC" "_1 1_2 EL 90 DN PVC" "PVC-Fitting" "0" "_1 1_2 EL 90 DN PVC.dwg")
    (list "_1 1_2 EL 90 PVC" "_1 1_2 EL 90 PVC" "PVC-Fitting" "0" "_1 1_2 EL 90 PVC.dwg")
    (list "_1 1_2 EL 90 UP PVC" "_1 1_2 EL 90 UP PVC" "PVC-Fitting" "0" "_1 1_2 EL 90 UP PVC.dwg")
    (list "_1 1_2 TEE DN PVC" "_1 1_2 TEE DN PVC" "PVC-Fitting" "0" "_1 1_2 TEE DN PVC.dwg")
    (list "_1 1_2 TEE PVC" "_1 1_2 TEE PVC" "PVC-Fitting" "0" "_1 1_2 TEE PVC.dwg")
    (list "_1 1_2 TEE UP PVC" "_1 1_2 TEE UP PVC" "PVC-Fitting" "0" "_1 1_2 TEE UP PVC.dwg")
    (list "_1 1_2 UNION PVC" "_1 1_2 UNION PVC" "PVC-Fitting" "0" "_1 1_2 UNION PVC.dwg")
    (list "_3_4 1_2 RED PVC" "_3_4 1_2 RED PVC" "PVC-Fitting" "0" "_3_4 1_2 RED PVC.dwg")
    (list "_3_4 ADP SXM PVC" "_3_4 ADP SXM PVC" "PVC-Fitting" "0" "_3_4 ADP SXM PVC.dwg")
    (list "_3_4 BALL PVC" "_3_4 BALL PVC" "PVC-Fitting" "0" "_3_4 BALL PVC.dwg")
    (list "_3_4 CAP PVC" "_3_4 CAP PVC" "PVC-Fitting" "0" "_3_4 CAP PVC.dwg")
    (list "_3_4 COUPLING PVC" "_3_4 COUPLING PVC" "PVC-Fitting" "0" "_3_4 COUPLING PVC.dwg")
    (list "_3_4 CROSS PVC" "_3_4 CROSS PVC" "PVC-Fitting" "0" "_3_4 CROSS PVC.dwg")
    (list "_3_4 EL 22 DN PVC" "_3_4 EL 22 DN PVC" "PVC-Fitting" "0" "_3_4 EL 22 DN PVC.dwg")
    (list "_3_4 EL 22 PVC" "_3_4 EL 22 PVC" "PVC-Fitting" "0" "_3_4 EL 22 PVC.dwg")
    (list "_3_4 EL 22 UP PVC" "_3_4 EL 22 UP PVC" "PVC-Fitting" "0" "_3_4 EL 22 UP PVC.dwg")
    (list "_3_4 EL 45 DN PVC" "_3_4 EL 45 DN PVC" "PVC-Fitting" "0" "_3_4 EL 45 DN PVC.dwg")
    (list "_3_4 EL 45 PVC" "_3_4 EL 45 PVC" "PVC-Fitting" "0" "_3_4 EL 45 PVC.dwg")
    (list "_3_4 EL 45 UP PVC" "_3_4 EL 45 UP PVC" "PVC-Fitting" "0" "_3_4 EL 45 UP PVC.dwg")
    (list "_3_4 EL 90 DN PVC" "_3_4 EL 90 DN PVC" "PVC-Fitting" "0" "_3_4 EL 90 DN PVC.dwg")
    (list "_3_4 EL 90 PVC" "_3_4 EL 90 PVC" "PVC-Fitting" "0" "_3_4 EL 90 PVC.dwg")
    (list "_3_4 EL 90 UP PVC" "_3_4 EL 90 UP PVC" "PVC-Fitting" "0" "_3_4 EL 90 UP PVC.dwg")
    (list "_3_4 TEE DN PVC" "_3_4 TEE DN PVC" "PVC-Fitting" "0" "_3_4 TEE DN PVC.dwg")
    (list "_3_4 TEE PVC" "_3_4 TEE PVC" "PVC-Fitting" "0" "_3_4 TEE PVC.dwg")
    (list "_3_4 TEE UP PVC" "_3_4 TEE UP PVC" "PVC-Fitting" "0" "_3_4 TEE UP PVC.dwg")
    (list "_3_4 UNION PVC" "_3_4 UNION PVC" "PVC-Fitting" "0" "_3_4 UNION PVC.dwg")
    (list "01 1_2 RED PVC" "01 1_2 RED PVC" "PVC-Fitting" "0" "01 1_2 RED PVC.dwg")
    (list "01 3_4 RED PVC" "01 3_4 RED PVC" "PVC-Fitting" "0" "01 3_4 RED PVC.dwg")
    (list "01 ADP SXM PVC" "01 ADP SXM PVC" "PVC-Fitting" "0" "01 ADP SXM PVC.dwg")
    (list "01 BALL PVC" "01 BALL PVC" "PVC-Fitting" "0" "01 BALL PVC.dwg")
    (list "01 CAP PVC" "01 CAP PVC" "PVC-Fitting" "0" "01 CAP PVC.dwg")
    (list "01 COUPLING PVC" "01 COUPLING PVC" "PVC-Fitting" "0" "01 COUPLING PVC.dwg")
    (list "01 CROSS PVC" "01 CROSS PVC" "PVC-Fitting" "0" "01 CROSS PVC.dwg")
    (list "01 EL 22 DN PVC" "01 EL 22 DN PVC" "PVC-Fitting" "0" "01 EL 22 DN PVC.dwg")
    (list "01 EL 22 PVC" "01 EL 22 PVC" "PVC-Fitting" "0" "01 EL 22 PVC.dwg")
    (list "01 EL 22 UP PVC" "01 EL 22 UP PVC" "PVC-Fitting" "0" "01 EL 22 UP PVC.dwg")
    (list "01 EL 45 DN PVC" "01 EL 45 DN PVC" "PVC-Fitting" "0" "01 EL 45 DN PVC.dwg")
    (list "01 EL 45 PVC" "01 EL 45 PVC" "PVC-Fitting" "0" "01 EL 45 PVC.dwg")
    (list "01 EL 45 UP PVC" "01 EL 45 UP PVC" "PVC-Fitting" "0" "01 EL 45 UP PVC.dwg")
    (list "01 EL 90 DN PVC" "01 EL 90 DN PVC" "PVC-Fitting" "0" "01 EL 90 DN PVC.dwg")
    (list "01 EL 90 PVC" "01 EL 90 PVC" "PVC-Fitting" "0" "01 EL 90 PVC.dwg")
    (list "01 EL 90 UP PVC" "01 EL 90 UP PVC" "PVC-Fitting" "0" "01 EL 90 UP PVC.dwg")
    (list "01 TEE DN PVC" "01 TEE DN PVC" "PVC-Fitting" "0" "01 TEE DN PVC.dwg")
    (list "01 TEE PVC" "01 TEE PVC" "PVC-Fitting" "0" "01 TEE PVC.dwg")
    (list "01 TEE UP PVC" "01 TEE UP PVC" "PVC-Fitting" "0" "01 TEE UP PVC.dwg")
    (list "01 UNION PVC" "01 UNION PVC" "PVC-Fitting" "0" "01 UNION PVC.dwg")
    (list "02 1 1_2 RED PVC" "02 1 1_2 RED PVC" "PVC-Fitting" "0" "02 1 1_2 RED PVC.dwg")
    (list "02 01 RED PVC" "02 01 RED PVC" "PVC-Fitting" "0" "02 01 RED PVC.dwg")
    (list "02 1_2 RED PVC" "02 1_2 RED PVC" "PVC-Fitting" "0" "02 1_2 RED PVC.dwg")
    (list "02 3_4 RED PVC" "02 3_4 RED PVC" "PVC-Fitting" "0" "02 3_4 RED PVC.dwg")
    (list "02 ADP SXM PVC" "02 ADP SXM PVC" "PVC-Fitting" "0" "02 ADP SXM PVC.dwg")
    (list "02 BALL PVC" "02 BALL PVC" "PVC-Fitting" "0" "02 BALL PVC.dwg")
    (list "02 CAP PVC" "02 CAP PVC" "PVC-Fitting" "0" "02 CAP PVC.dwg")
    (list "02 COUPLING PVC" "02 COUPLING PVC" "PVC-Fitting" "0" "02 COUPLING PVC.dwg")
    (list "02 CROSS PVC" "02 CROSS PVC" "PVC-Fitting" "0" "02 CROSS PVC.dwg")
    (list "02 EL 22 DN PVC" "02 EL 22 DN PVC" "PVC-Fitting" "0" "02 EL 22 DN PVC.dwg")
    (list "02 EL 22 PVC" "02 EL 22 PVC" "PVC-Fitting" "0" "02 EL 22 PVC.dwg")
    (list "02 EL 22 UP PVC" "02 EL 22 UP PVC" "PVC-Fitting" "0" "02 EL 22 UP PVC.dwg")
    (list "02 EL 45 DN PVC" "02 EL 45 DN PVC" "PVC-Fitting" "0" "02 EL 45 DN PVC.dwg")
    (list "02 EL 45 PVC" "02 EL 45 PVC" "PVC-Fitting" "0" "02 EL 45 PVC.dwg")
    (list "02 EL 45 UP PVC" "02 EL 45 UP PVC" "PVC-Fitting" "0" "02 EL 45 UP PVC.dwg")
    (list "02 EL 90 DN PVC" "02 EL 90 DN PVC" "PVC-Fitting" "0" "02 EL 90 DN PVC.dwg")
    (list "02 EL 90 PVC" "02 EL 90 PVC" "PVC-Fitting" "0" "02 EL 90 PVC.dwg")
    (list "02 EL 90 UP PVC" "02 EL 90 UP PVC" "PVC-Fitting" "0" "02 EL 90 UP PVC.dwg")
    (list "02 TEE DN PVC" "02 TEE DN PVC" "PVC-Fitting" "0" "02 TEE DN PVC.dwg")
    (list "02 TEE PVC" "02 TEE PVC" "PVC-Fitting" "0" "02 TEE PVC.dwg")
    (list "02 TEE UP PVC" "02 TEE UP PVC" "PVC-Fitting" "0" "02 TEE UP PVC.dwg")
    (list "02 UNION PVC" "02 UNION PVC" "PVC-Fitting" "0" "02 UNION PVC.dwg")
    (list "03 1 1_2 RED PVC" "03 1 1_2 RED PVC" "PVC-Fitting" "0" "03 1 1_2 RED PVC.dwg")
    (list "03 01 RED PVC" "03 01 RED PVC" "PVC-Fitting" "0" "03 01 RED PVC.dwg")
    (list "03 02 RED PVC" "03 02 RED PVC" "PVC-Fitting" "0" "03 02 RED PVC.dwg")
    (list "03 3_4 RED PVC" "03 3_4 RED PVC" "PVC-Fitting" "0" "03 3_4 RED PVC.dwg")
    (list "03 ADP SXM PVC" "03 ADP SXM PVC" "PVC-Fitting" "0" "03 ADP SXM PVC.dwg")
    (list "03 BALL PVC" "03 BALL PVC" "PVC-Fitting" "0" "03 BALL PVC.dwg")
    (list "03 CAP PVC" "03 CAP PVC" "PVC-Fitting" "0" "03 CAP PVC.dwg")
    (list "03 COUPLING PVC" "03 COUPLING PVC" "PVC-Fitting" "0" "03 COUPLING PVC.dwg")
    (list "03 CROSS PVC" "03 CROSS PVC" "PVC-Fitting" "0" "03 CROSS PVC.dwg")
    (list "03 EL 22 DN PVC" "03 EL 22 DN PVC" "PVC-Fitting" "0" "03 EL 22 DN PVC.dwg")
    (list "03 EL 22 PVC" "03 EL 22 PVC" "PVC-Fitting" "0" "03 EL 22 PVC.dwg")
    (list "03 EL 22 UP PVC" "03 EL 22 UP PVC" "PVC-Fitting" "0" "03 EL 22 UP PVC.dwg")
    (list "03 EL 45 DN PVC" "03 EL 45 DN PVC" "PVC-Fitting" "0" "03 EL 45 DN PVC.dwg")
    (list "03 EL 45 PVC" "03 EL 45 PVC" "PVC-Fitting" "0" "03 EL 45 PVC.dwg")
    (list "03 EL 45 UP PVC" "03 EL 45 UP PVC" "PVC-Fitting" "0" "03 EL 45 UP PVC.dwg")
    (list "03 EL 90 DN PVC" "03 EL 90 DN PVC" "PVC-Fitting" "0" "03 EL 90 DN PVC.dwg")
    (list "03 EL 90 PVC" "03 EL 90 PVC" "PVC-Fitting" "0" "03 EL 90 PVC.dwg")
    (list "03 EL 90 UP PVC" "03 EL 90 UP PVC" "PVC-Fitting" "0" "03 EL 90 UP PVC.dwg")
    (list "03 TEE DN PVC" "03 TEE DN PVC" "PVC-Fitting" "0" "03 TEE DN PVC.dwg")
    (list "03 TEE PVC" "03 TEE PVC" "PVC-Fitting" "0" "03 TEE PVC.dwg")
    (list "03 TEE UP PVC" "03 TEE UP PVC" "PVC-Fitting" "0" "03 TEE UP PVC.dwg")
    ;; -- SCWA (8 blocks) --
    (list "SCWA - Directional Arrow & Text - Left" "SCWA ARR DIRECTIONAL LT" "SCWA" "0" "SCWA ARR DIRECTIONAL LT.dwg")
    (list "SCWA - Directional Arrow & Text - Right" "SCWA ARR DIRECTIONAL RT" "SCWA" "0" "SCWA ARR DIRECTIONAL RT.dwg")
    (list "SCWA - Grade Stick - Left" "SCWA GRADE STICK LT" "SCWA" "0" "SCWA GRADE STICK LT.dwg")
    (list "SCWA - Grade Stick - Right" "SCWA GRADE STICK RT" "SCWA" "0" "SCWA GRADE STICK RT.dwg")
    (list "SCWA - Section - Left" "SCWA SECTION LT" "SCWA" "0" "SCWA SECTION LT.dwg")
    (list "SCWA - Section - Right" "SCWA SECTION RT" "SCWA" "0" "SCWA SECTION RT.dwg")
    (list "SCWA - Title - Section with Bubble - \"Not To Scale\"" "SCWA TITLE SECTION" "SCWA" "0" "SCWA TITLE SECTION.dwg")
    (list "SCWA - Cover Sheet" "SCWA TB 22x34" "SCWA" "0" "SCWA TB 22x34.dwg")
    ;; -- SEALS & LOGOS (23 blocks) --
    (list "B&R Logo" "LOGO BR2" "Seals & Logos" "0" "LOGO BR2.dwg")
    (list "B&R Logo" "LOGO BR1" "Seals & Logos" "0" "LOGO BR1.dwg")
    (list "Seal Date" "SEAL DATE" "Seals & Logos" "0" "SEAL DATE.dwg")
    (list "Ben Bryant" "SEAL BLB-BEN" "Seals & Logos" "0" "SEAL BLB-BEN.dwg")
    (list "Brent Beazor" "SEAL BLB" "Seals & Logos" "0" "SEAL BLB.dwg")
    (list "Dave Coleman" "SEAL DYC" "Seals & Logos" "0" "SEAL DYC.dwg")
    (list "Jeff Roach" "SEAL JDR" "Seals & Logos" "0" "SEAL JDR.dwg")
    (list "John Thompson" "SEAL JST" "Seals & Logos" "0" "SEAL JST.dwg")
    (list "Paul Bartholow" "SEAL PVB" "Seals & Logos" "0" "SEAL PVB.dwg")
    (list "Sean Jeane" "SEAL MSJ" "Seals & Logos" "0" "SEAL MSJ.dwg")
    (list "Brent Beazor SIG" "SIGNATURE BLB" "Seals & Logos" "0" "SIGNATURE BLB.dwg")
    (list "Dave Coleman SIG" "SIGNATURE DYC" "Seals & Logos" "0" "SIGNATURE DYC.dwg")
    (list "Jack Locey" "SEAL JSL" "Seals & Logos" "0" "SEAL JSL.dwg")
    (list "Jack Locey SIG" "SIGNATURE JSL" "Seals & Logos" "0" "SIGNATURE JSL.dwg")
    (list "Paul Bartholow SIG" "SIGNATURE PVB" "Seals & Logos" "0" "SIGNATURE PVB.dwg")
    (list "John Thompson SIG" "SIGNATURE JST" "Seals & Logos" "0" "SIGNATURE JST.dwg")
    (list "Sean Jeane SIG" "SIGNATURE MSJ" "Seals & Logos" "0" "SIGNATURE MSJ.dwg")
    (list "Bradford Hoffman - Santa Rosa" "SEAL SR BLH" "Seals & Logos" "0" "SEAL SR BLH.dwg")
    (list "David Guhin - Santa Rosa" "SEAL SR DMG" "Seals & Logos" "0" "SEAL SR DMG.dwg")
    (list "Jason Nutt - Santa Rosa" "SEAL SR JLN" "Seals & Logos" "0" "SEAL SR JLN.dwg")
    (list "Shannon Cotulla - TOW" "SEAL TOW SDC" "Seals & Logos" "0" "SEAL TOW SDC.dwg")
    (list "Jeff Roach SIG" "SIGNATURE JDR" "Seals & Logos" "0" "SIGNATURE JDR.dwg")
    (list "Ben Bryant SIG" "SIGNATURE BLB-BEN" "Seals & Logos" "0" "SIGNATURE BLB-BEN.dwg")
    ;; -- SHEET NOTES (67 blocks) --
    (list "Sheet Note Title" "NOTE SHEET SETUP TITLE" "Sheet Notes" "0" "NOTE SHEET SETUP TITLE.dwg")
    (list "Sheet Note Setup - (insert then use notes within drawing)" "NOTE SHEET SETUP" "Sheet Notes" "0" "NOTE SHEET SETUP.dwg")
    (list "Sheet Note Setup - Multiple Drawings - (where notes occur in different drawings)" "NOTE SHEET SETUP MULTIPLE DRAWING NOTES" "Sheet Notes" "0" "NOTE SHEET SETUP MULTIPLE DRAWING NOTES.dwg")
    (list "Sheet Note Setup - Piping - (insert then use notes within drawing)" "NOTE SHEET SETUP PIPING" "Sheet Notes" "0" "NOTE SHEET SETUP PIPING.dwg")
    (list "Sheet Note Setup - Demolition" "NOTE SHEET SETUP DEMOLITION" "Sheet Notes" "0" "NOTE SHEET SETUP DEMOLITION.dwg")
    (list "Sheet Note Setup - Oval" "NOTE SHEET SETUP OVAL" "Sheet Notes" "0" "NOTE SHEET SETUP OVAL.dwg")
    (list "Sheet Note Setup - Square" "NOTE SHEET SETUP SQUARE" "Sheet Notes" "0" "NOTE SHEET SETUP SQUARE.dwg")
    (list "Sheet Note Title - Narrow" "NOTE SHEET SETUP TITLE NARROW" "Sheet Notes" "0" "NOTE SHEET SETUP TITLE NARROW.DWG")
    (list "Sheet Note Setup - Narrow" "NOTE SHEET SETUP NARROW" "Sheet Notes" "0" "NOTE SHEET SETUP NARROW.DWG")
    (list "Note Setup - Use for MText Notes in Paper Space" "NOTE SETUP" "Sheet Notes" "0" "NOTE SETUP.dwg")
    (list "Sheet Note Setup - SR C01-SR C30" "NOTE SHEET SETUP OVAL SR C01-SR C30" "Sheet Notes" "0" "NOTE SHEET SETUP OVAL SR C01-SR C30.dwg")
    (list "Sheet Note Setup - SR D01-SR D30" "NOTE SHEET SETUP OVAL SR D01-SR D30" "Sheet Notes" "0" "NOTE SHEET SETUP OVAL SR D01-SR D30.dwg")
    (list "Sheet Note Setup - SR R01-SR R30" "NOTE SHEET SETUP OVAL SR R01-SR R30" "Sheet Notes" "0" "NOTE SHEET SETUP OVAL SR R01-SR R30.dwg")
    (list "Sheet Note Setup - SR S01-SR S30" "NOTE SHEET SETUP OVAL SR S01-SR S30" "Sheet Notes" "0" "NOTE SHEET SETUP OVAL SR S01-SR S30.dwg")
    (list "Sheet Note Setup - SR T01-SR T30" "NOTE SHEET SETUP OVAL SR T01-SR T30" "Sheet Notes" "0" "NOTE SHEET SETUP OVAL SR T01-SR T30.dwg")
    (list "Sheet Note Setup - SR W01-SR W30" "NOTE SHEET SETUP OVAL SR W01-SR W30" "Sheet Notes" "0" "NOTE SHEET SETUP OVAL SR W01-SR W30.dwg")
    (list "Sheet Note Setup - SR X01-SR X30" "NOTE SHEET SETUP OVAL SR X01-SR X30" "Sheet Notes" "0" "NOTE SHEET SETUP OVAL SR X01-SR X30.dwg")
    (list "Sheet Note 01" "NOTE SHEET 01" "Sheet Notes" "0" "NOTE SHEET 01.dwg")
    (list "Sheet Note 02" "NOTE SHEET 02" "Sheet Notes" "0" "NOTE SHEET 02.dwg")
    (list "Sheet Note 03" "NOTE SHEET 03" "Sheet Notes" "0" "NOTE SHEET 03.dwg")
    (list "Sheet Note 04" "NOTE SHEET 04" "Sheet Notes" "0" "NOTE SHEET 04.dwg")
    (list "Sheet Note 05" "NOTE SHEET 05" "Sheet Notes" "0" "NOTE SHEET 05.dwg")
    (list "Sheet Note 06" "NOTE SHEET 06" "Sheet Notes" "0" "NOTE SHEET 06.dwg")
    (list "Sheet Note 07" "NOTE SHEET 07" "Sheet Notes" "0" "NOTE SHEET 07.dwg")
    (list "Sheet Note 08" "NOTE SHEET 08" "Sheet Notes" "0" "NOTE SHEET 08.dwg")
    (list "Sheet Note 09" "NOTE SHEET 09" "Sheet Notes" "0" "NOTE SHEET 09.dwg")
    (list "Sheet Note 10" "NOTE SHEET 10" "Sheet Notes" "0" "NOTE SHEET 10.dwg")
    (list "Sheet Note 11" "NOTE SHEET 11" "Sheet Notes" "0" "NOTE SHEET 11.dwg")
    (list "Sheet Note 12" "NOTE SHEET 12" "Sheet Notes" "0" "NOTE SHEET 12.dwg")
    (list "Sheet Note 13" "NOTE SHEET 13" "Sheet Notes" "0" "NOTE SHEET 13.dwg")
    (list "Sheet Note 14" "NOTE SHEET 14" "Sheet Notes" "0" "NOTE SHEET 14.dwg")
    (list "Sheet Note 15" "NOTE SHEET 15" "Sheet Notes" "0" "NOTE SHEET 15.dwg")
    (list "Sheet Note 16" "NOTE SHEET 16" "Sheet Notes" "0" "NOTE SHEET 16.dwg")
    (list "Sheet Note 17" "NOTE SHEET 17" "Sheet Notes" "0" "NOTE SHEET 17.dwg")
    (list "Sheet Note 18" "NOTE SHEET 18" "Sheet Notes" "0" "NOTE SHEET 18.dwg")
    (list "Sheet Note 19" "NOTE SHEET 19" "Sheet Notes" "0" "NOTE SHEET 19.dwg")
    (list "Sheet Note 20" "NOTE SHEET 20" "Sheet Notes" "0" "NOTE SHEET 20.dwg")
    (list "Sheet Note 21" "NOTE SHEET 21" "Sheet Notes" "0" "NOTE SHEET 21.dwg")
    (list "Sheet Note 22" "NOTE SHEET 22" "Sheet Notes" "0" "NOTE SHEET 22.dwg")
    (list "Sheet Note 23" "NOTE SHEET 23" "Sheet Notes" "0" "NOTE SHEET 23.dwg")
    (list "Sheet Note 24" "NOTE SHEET 24" "Sheet Notes" "0" "NOTE SHEET 24.dwg")
    (list "Sheet Note 25" "NOTE SHEET 25" "Sheet Notes" "0" "NOTE SHEET 25.dwg")
    (list "Sheet Note 26" "NOTE SHEET 26" "Sheet Notes" "0" "NOTE SHEET 26.dwg")
    (list "Sheet Note 27" "NOTE SHEET 27" "Sheet Notes" "0" "NOTE SHEET 27.dwg")
    (list "Sheet Note 28" "NOTE SHEET 28" "Sheet Notes" "0" "NOTE SHEET 28.dwg")
    (list "Sheet Note 29" "NOTE SHEET 29" "Sheet Notes" "0" "NOTE SHEET 29.dwg")
    (list "Sheet Note 30" "NOTE SHEET 30" "Sheet Notes" "0" "NOTE SHEET 30.dwg")
    (list "Sheet Note 31" "NOTE SHEET 31" "Sheet Notes" "0" "NOTE SHEET 31.dwg")
    (list "Sheet Note 32" "NOTE SHEET 32" "Sheet Notes" "0" "NOTE SHEET 32.dwg")
    (list "Sheet Note 33" "NOTE SHEET 33" "Sheet Notes" "0" "NOTE SHEET 33.dwg")
    (list "Sheet Note 34" "NOTE SHEET 34" "Sheet Notes" "0" "NOTE SHEET 34.dwg")
    (list "Sheet Note 35" "NOTE SHEET 35" "Sheet Notes" "0" "NOTE SHEET 35.dwg")
    (list "Sheet Note 36" "NOTE SHEET 36" "Sheet Notes" "0" "NOTE SHEET 36.dwg")
    (list "Sheet Note 37" "NOTE SHEET 37" "Sheet Notes" "0" "NOTE SHEET 37.dwg")
    (list "Sheet Note 38" "NOTE SHEET 38" "Sheet Notes" "0" "NOTE SHEET 38.dwg")
    (list "Sheet Note 39" "NOTE SHEET 39" "Sheet Notes" "0" "NOTE SHEET 39.dwg")
    (list "Sheet Note 40" "NOTE SHEET 40" "Sheet Notes" "0" "NOTE SHEET 40.dwg")
    (list "Sheet Note 41" "NOTE SHEET 41" "Sheet Notes" "0" "NOTE SHEET 41.dwg")
    (list "Sheet Note 42" "NOTE SHEET 42" "Sheet Notes" "0" "NOTE SHEET 42.dwg")
    (list "Sheet Note 43" "NOTE SHEET 43" "Sheet Notes" "0" "NOTE SHEET 43.dwg")
    (list "Sheet Note 44" "NOTE SHEET 44" "Sheet Notes" "0" "NOTE SHEET 44.dwg")
    (list "Sheet Note 45" "NOTE SHEET 45" "Sheet Notes" "0" "NOTE SHEET 45.dwg")
    (list "Sheet Note 46" "NOTE SHEET 46" "Sheet Notes" "0" "NOTE SHEET 46.dwg")
    (list "Sheet Note 47" "NOTE SHEET 47" "Sheet Notes" "0" "NOTE SHEET 47.dwg")
    (list "Sheet Note 48" "NOTE SHEET 48" "Sheet Notes" "0" "NOTE SHEET 48.dwg")
    (list "Sheet Note 49" "NOTE SHEET 49" "Sheet Notes" "0" "NOTE SHEET 49.dwg")
    (list "Sheet Note 50" "NOTE SHEET 50" "Sheet Notes" "0" "NOTE SHEET 50.dwg")
    ;; -- SURVEY (20 blocks) --
    (list "TOPO SETUP - 10 Scale" "$BR PROT-topo" "Survey" "0" "$BR PROT-topo.dwg")
    (list "Tree - Save" "TREE SAVE" "Survey" "0" "TREE SAVE.dwg")
    (list "Tree - Remove" "TREE REMOVE" "Survey" "0" "TREE REMOVE.dwg")
    (list "Project Site Arrow" "ARR PROJECT" "Survey" "0" "ARR PROJECT.dwg")
    (list "Star" "STAR" "Survey" "0" "STAR.dwg")
    (list "Landhook" "LANDHOOK" "Survey" "0" "LANDHOOK.dwg")
    (list "Benchmark" "SVY BENCHMARK" "Survey" "0" "SVY BENCHMARK.dwg")
    (list "Control Station" "SVY CONTROL" "Survey" "0" "SVY CONTROL.dwg")
    (list "Found Monument Destroyed" "SVY MON FND DISTROYED" "Survey" "0" "SVY MON FND DISTROYED.dwg")
    (list "Found Well Monument" "SVY MON FND WELL" "Survey" "0" "SVY MON FND WELL.dwg")
    (list "Found Concrete Monument" "SVY MON FND CONC" "Survey" "0" "SVY MON FND CONC.dwg")
    (list "Found Iron Pipe" "SVY MON FND IP" "Survey" "0" "SVY MON FND IP.dwg")
    (list "Found T-Bar" "SVY MON FND TBAR" "Survey" "0" "SVY MON FND TBAR.dwg")
    (list "Set Well Monument" "SVY MON SET WELL" "Survey" "0" "SVY MON SET WELL.dwg")
    (list "Set Iron Pipe" "SVY MON SET IP" "Survey" "0" "SVY MON SET IP.dwg")
    (list "Set Tag" "SVY MON SET TAG" "Survey" "0" "SVY MON SET TAG.dwg")
    (list "Break" "BREAK" "Survey" "0" "BREAK.dwg")
    (list "Crows Feet" "CROWS FEET" "Survey" "0" "CROWS FEET.dwg")
    (list "Tik" "TIK" "Survey" "0" "TIK.DWG")
    (list "Wiggle" "WIGGLE" "Survey" "0" "WIGGLE.dwg")
    ;; -- TB (38 blocks) --
    (list "Project Site Arrow" "ARR PROJECT" "TB" "0" "ARR PROJECT.dwg")
    (list "Star" "STAR" "TB" "0" "STAR.dwg")
    (list "Guide Lines - Dynamic - Insert into Title Block" "TB GUIDE" "TB" "0" "TB GUIDE.dwg")
    (list "Setup - Index Of Sheets - Use without SheetSet" "TB INDEX OF SHEETS1" "TB" "0" "TB INDEX OF SHEETS1.dwg")
    (list "Setup - Index Of Sheets - Use with SheetSet" "TB INDEX OF SHEETS2" "TB" "0" "TB INDEX OF SHEETS2.dwg")
    (list "Setup - Benchmark - Earthwork - Owner - Purpose - As Needed" "TB COVER BR BM EARTHWORK OWNER PURPOSE" "TB" "0" "TB COVER BR BM EARTHWORK OWNER PURPOSE.dwg")
    (list "Setup - Purpose - Owner - Benchmark - Earthwork - As Needed" "TB COVER BR BM EARTHWORK OWNER PURPOSE" "TB" "0" "TB COVER BR BM EARTHWORK OWNER PURPOSE.dwg")
    (list "Setup - Board Of Directors - As Needed on Cover Sheet" "TB COVER BR BOARD OF DIRECTORS" "TB" "0" "TB COVER BR BOARD OF DIRECTORS.dwg")
    (list "Setup - City Council - As Needed on Cover Sheet" "TB COVER BR CITY COUNCIL" "TB" "0" "TB COVER BR CITY COUNCIL.dwg")
    (list "B&R 11x17 - Cover Sheet" "TB COVER BR 11x17" "TB" "0" "TB COVER BR 11x17.dwg")
    (list "B&R 22x34 - Cover Sheet" "TB COVER BR 22x34" "TB" "0" "TB COVER BR 22x34.dwg")
    (list "B&R 24x36 - Cover Sheet" "TB COVER BR 24x36" "TB" "0" "TB COVER BR 24x36.dwg")
    (list "B&R 30x42 - Cover Sheet" "TB COVER BR 30x42" "TB" "0" "TB COVER BR 30x42.dwg")
    (list "B&R 24x36 - Tentative Map - Sheet 1" "TB TENT BR 24x36-S1" "TB" "0" "TB TENT BR 24x36-S1.dwg")
    (list "B&R 24x36 - Tentative Map - Sheet 2" "TB TENT BR 24x36-S2" "TB" "0" "TB TENT BR 24x36-S2.dwg")
    (list "B&R 30x42 - Tentative Map - Sheet 1" "TB TENT BR 30x42-S1" "TB" "0" "TB TENT BR 30x42-S1.dwg")
    (list "B&R 30x42 - Tentative Map - Sheet 2" "TB TENT BR 30x42-S2" "TB" "0" "TB TENT BR 30x42-S2.dwg")
    (list "B&R 8x11 - Border Only" "TB EXHIBIT BR 08X11 BORDER ONLY" "TB" "0" "TB EXHIBIT BR 08X11 BORDER ONLY.dwg")
    (list "B&R 8x11 - Exhibit" "TB EXHIBIT BR 08x11-1" "TB" "0" "TB EXHIBIT BR 08x11-1.dwg")
    (list "B&R 8x11 - Exhibit - Use in Report" "TB EXHIBIT BR 08X11-3" "TB" "0" "TB EXHIBIT BR 08X11-3.dwg")
    (list "B&R 11x17 - Exhibit - Use in Report" "TB EXHIBIT BR 11x17-3" "TB" "0" "TB EXHIBIT BR 11x17-3.dwg")
    (list "B&R 11x17 - Exhibit-1" "TB EXHIBIT BR 11x17-1" "TB" "0" "TB EXHIBIT BR 11x17-1.dwg")
    (list "B&R 24x36 - Exhibit" "TB EXHIBIT BR 24x36-2" "TB" "0" "TB EXHIBIT BR 24x36-2.dwg")
    (list "B&R 30x42 - Exhibit" "TB EXHIBIT BR 30x42-2" "TB" "0" "TB EXHIBIT BR 30x42-2.dwg")
    (list "B&R 24x36 - Exhibit - SWLID Existing" "TB EXHIBIT SWLID EXISTING" "TB" "0" "TB EXHIBIT SWLID EXISTING.dwg")
    (list "B&R 24x36 - Exhibit - SWLID Proposed" "TB EXHIBIT SWLID PROPOSED" "TB" "0" "TB EXHIBIT SWLID PROPOSED.dwg")
    (list "B&R 8x11 - Rsheet" "TB RSHEET BR 08x11" "TB" "0" "TB RSHEET BR 08x11.dwg")
    (list "Santa Rosa 8x11 - Rsheet" "TB RSHEET SR 08x11" "TB" "0" "TB RSHEET SR 08x11.DWG")
    (list "Town of Windsor 24x36 - Cover Sheet" "TB COVER TOW 24x36" "TB" "0" "TB COVER TOW 24x36.dwg")
    (list "Town of Windsor 24x36 - Cover Sheet - Outside Water" "TB COVER TOW OUTSIDE WATER 24x36" "TB" "0" "TB COVER TOW OUTSIDE WATER 24x36.dwg")
    (list "QKA 8x11" "TB EXHIBIT QKA 08x11" "TB" "0" "TB EXHIBIT QKA 08x11.dwg")
    (list "QKA 11x17" "TB EXHIBIT QKA 11x17" "TB" "0" "TB EXHIBIT QKA 11x17.dwg")
    (list "B&R 8x11 - Frame Only" "TB TRIM LINE BR 08x11" "TB" "0" "TB TRIM LINE BR 08x11.DWG")
    (list "B&R 11x17 - Frame Only" "TB TRIM LINE BR 11x17" "TB" "0" "TB TRIM LINE BR 11x17.DWG")
    (list "B&R 18x26 - Frame Only" "TB TRIM LINE BR 18x26" "TB" "0" "TB TRIM LINE BR 18x26.DWG")
    (list "B&R 24x36 - Frame Only" "TB TRIM LINE BR 24x36" "TB" "0" "TB TRIM LINE BR 24x36.DWG")
    (list "B&R 30x42 - Frame Only" "TB TRIM LINE BR 30x42" "TB" "0" "TB TRIM LINE BR 30x42.DWG")
    (list "Custom Border - Dynamic" "TB CUSTOM" "TB" "0" "TB CUSTOM.dwg")
    ;; -- TB-DATA (20 blocks) --
    (list "TB DATA BR 11x17" "TB DATA BR 11x17" "TB-DATA" "0" "TB DATA BR 11x17.dwg")
    (list "TB DATA BR 22x34" "TB DATA BR 22x34" "TB-DATA" "0" "TB DATA BR 22x34.dwg")
    (list "TB DATA BR 22x34 - With Drawing Number" "TB DATA BR 22x34-WITH DWG NUMBER" "TB-DATA" "0" "TB DATA BR 22x34-WITH DWG NUMBER.dwg")
    (list "TB DATA BR 24x36" "TB DATA BR 24x36" "TB-DATA" "0" "TB DATA BR 24x36.dwg")
    (list "TB DATA BR 30x42" "TB DATA BR 30x42" "TB-DATA" "0" "TB DATA BR 30x42.dwg")
    (list "TB DATA AXIA 24x36" "TB DATA AXIA 24x36" "TB-DATA" "0" "TB DATA AXIA 24x36.dwg")
    (list "TB DATA BAR 24x36 EXHIBIT" "TB DATA BAR 24x36 EXHIBIT" "TB-DATA" "0" "TB DATA BAR 24x36 EXHIBIT.dwg")
    (list "TB DATA BAR 30x42 EXHIBIT" "TB DATA BAR 30x42 EXHIBIT" "TB-DATA" "0" "TB DATA BAR 30x42 EXHIBIT.dwg")
    (list "TB DATA BAR 30x42" "TB DATA BAR 30x42" "TB-DATA" "0" "TB DATA BAR 30x42.dwg")
    (list "TB DATA DAN HARDIN 24x36" "TB DATA DAN HARDIN 24x36" "TB-DATA" "0" "TB DATA DAN HARDIN 24x36.dwg")
    (list "TB DATA DSA 24x36" "TB DATA DSA 24x36" "TB-DATA" "0" "TB DATA DSA 24x36.dwg")
    (list "TB DATA DSA 30x42" "TB DATA DSA 30x42" "TB-DATA" "0" "TB DATA DSA 30x42.dwg")
    (list "TB DATA QKA 24x36" "TB DATA QKA 24x36" "TB-DATA" "0" "TB DATA QKA 24x36.dwg")
    (list "TB DATA QKA 24x36 Logo & Seal" "TB DATA QKA 24x36 LOGO & SEAL" "TB-DATA" "0" "TB DATA QKA 24x36 LOGO & SEAL.dwg")
    (list "TB DATA QKA 30x42" "TB DATA QKA 30x42" "TB-DATA" "0" "TB DATA QKA 30x42.DWG")
    (list "TB DATA QKA 30x42 Logo & Seal" "TB DATA QKA 30x42 LOGO & SEAL" "TB-DATA" "0" "TB DATA QKA 30x42 LOGO & SEAL.dwg")
    (list "TB DATA SR 22x34" "TB DATA SR 22x34" "TB-DATA" "0" "TB DATA SR 22x34.dwg")
    (list "TB DATA TLCD 24x36" "TB DATA TLCD 24x36" "TB-DATA" "0" "TB DATA TLCD 24x36.dwg")
    (list "TB DATA TLCD 30x42" "TB DATA TLCD 30x42" "TB-DATA" "0" "TB DATA TLCD 30x42.dwg")
    (list "TB DATA TOW 24x36" "TB DATA TOW 24x36" "TB-DATA" "0" "TB DATA TOW 24x36.dwg")
    ;; -- TOPO (123 blocks) --
    (list "TOPO SETUP - 10 Scale" "$BR PROT-topo" "Topo" "0" "$BR PROT-topo.dwg")
    (list "TOPO-utility by others note" "TOPO-utility by others note" "Topo" "0" "J:\\LIB\\BR\\$ - Legend - Topo.dwg")
    (list "Stamp - Basis of Bearing & Benchmark" "STAMP SVY BOB BM" "Topo" "0" "STAMP SVY BOB BM.DWG")
    (list "Text with Wiggle" "LABEL TEXT WITH WIGGLE" "Topo" "0" "LABEL TEXT WITH WIGGLE.dwg")
    (list "Circle - Filled" "CIRCLE SQUARE" "Topo" "0" "CIRCLE SQUARE.DWG")
    (list "Square - Filled" "CIRCLE SQUARE" "Topo" "0" "CIRCLE SQUARE.DWG")
    (list "Cap" "CAP" "Topo" "0" "CAP.DWG")
    (list "Pipe Break" "00 PIPE BREAK" "Topo" "0" "00 PIPE BREAK.dwg")
    (list "Slope" "SLOPE" "Topo" "0" "SLOPE.DWG")
    (list "Pavement Marking - ADA" "PAINT HC" "Topo" "0" "PAINT HC.dwg")
    (list "Pavement Marking - EV" "PAINT ELEC CHARGE" "Topo" "0" "PAINT ELEC CHARGE.dwg")
    (list "Compact" "PAINT COMPACT" "Topo" "0" "PAINT COMPACT.dwg")
    (list "Sign" "SIGN" "Topo" "0" "SIGN.dwg")
    (list "Pavement Marking - Bike" "PAINT BIKE" "Topo" "0" "PAINT BIKE.dwg")
    (list "Pavement Marking - Stop" "PAINT STOP" "Topo" "0" "PAINT STOP.dwg")
    (list "Wheel Stop" "WHEEL STOP" "Topo" "0" "WHEEL STOP.dwg")
    (list "ANTENNA" "ANTENNA" "Topo" "0" "ANTENNA.dwg")
    (list "BASKETBALL COURT" "BASKETBALL COURT" "Topo" "0" "BASKETBALL COURT.dwg")
    (list "BASKETBALL HOOP" "BASKETBALL HOOP" "Topo" "0" "BASKETBALL HOOP.dwg")
    (list "BENCH" "BENCH" "Topo" "0" "BENCH.dwg")
    (list "BIKE RACK" "BIKE RACK" "Topo" "0" "BIKE RACK.dwg")
    (list "BOLLARD" "BOLLARD" "Topo" "0" "BOLLARD.DWG")
    (list "CLEANOUT" "00 CLEANOUT" "Topo" "0" "00 CLEANOUT.DWG")
    (list "COLUMN" "COLUMN" "Topo" "0" "COLUMN.dwg")
    (list "DOOR" "DOOR1" "Topo" "0" "DOOR1.dwg")
    (list "DOOR" "DOOR2" "Topo" "0" "DOOR2.dwg")
    (list "GATE" "GATE" "Topo" "0" "GATE.dwg")
    (list "DOOR ELEVATION" "DOOR ELEVATION" "Topo" "0" "DOOR ELEVATION.dwg")
    (list "WINDOW DYNAMIC" "WINDOW DYNAMIC" "Topo" "0" "WINDOW DYNAMIC.dwg")
    (list "ELEC LIGHT - STANDARD" "ELEC LIGHT1" "Topo" "0" "ELEC LIGHT1.DWG")
    (list "ELEC LIGHT - DECORATIVE" "ELEC LIGHT2" "Topo" "0" "ELEC LIGHT2.dwg")
    (list "ELEC CAN" "ELEC CAN" "Topo" "0" "ELEC CAN.dwg")
    (list "ELEC MH" "ELEC MH" "Topo" "0" "ELEC MH.DWG")
    (list "ELEC PANEL" "ELEC PANEL" "Topo" "0" "ELEC PANEL.dwg")
    (list "ELEC SERVICE" "ELEC SERVICE" "Topo" "0" "ELEC SERVICE.DWG")
    (list "ELEC TOWER" "ELEC TOWER" "Topo" "0" "ELEC TOWER.dwg")
    (list "FLAG POLE" "FLAG POLE" "Topo" "0" "FLAG POLE.dwg")
    (list "RISER" "00 RISER" "Topo" "0" "00 RISER.dwg")
    (list "JOINT & UTILITY POLE" "JP" "Topo" "0" "JP.DWG")
    (list "GUY" "GUY" "Topo" "0" "GUY.DWG")
    (list "MH" "00 MH" "Topo" "0" "00 MH.dwg")
    (list "MAILBOX" "MAILBOX" "Topo" "0" "MAILBOX.dwg")
    (list "PAINT ARR CALTRANS LT" "PAINT ARR CALTRANS LT" "Topo" "0" "PAINT ARR CALTRANS LT.dwg")
    (list "PAINT ARR CALTRANS RT" "PAINT ARR CALTRANS RT" "Topo" "0" "PAINT ARR CALTRANS RT.dwg")
    (list "PAINT ARR LT" "PAINT ARR LT" "Topo" "0" "PAINT ARR LT.DWG")
    (list "PAINT ARR MERGE" "PAINT ARR MERGE" "Topo" "0" "PAINT ARR MERGE.dwg")
    (list "PAINT ARR RT" "PAINT ARR RT" "Topo" "0" "PAINT ARR RT.DWG")
    (list "PAINT ARR STRAIGHT" "PAINT ARR STRAIGHT" "Topo" "0" "PAINT ARR STRAIGHT.dwg")
    (list "PAINT BIKE" "PAINT BIKE" "Topo" "0" "PAINT BIKE.dwg")
    (list "PAINT COMPACT" "PAINT COMPACT" "Topo" "0" "PAINT COMPACT.dwg")
    (list "PAINT HC" "PAINT HC" "Topo" "0" "PAINT HC.dwg")
    (list "PAINT STOP" "PAINT STOP" "Topo" "0" "PAINT STOP.dwg")
    (list "PERSON MAN" "PERSON MAN" "Topo" "0" "PERSON MAN.dwg")
    (list "PROPANE" "PROPANE" "Topo" "0" "PROPANE.dwg")
    (list "PUMP" "PUMP1" "Topo" "0" "PUMP1.dwg")
    (list "PUMP" "PUMP2" "Topo" "0" "PUMP2.dwg")
    (list "RIPRAP" "RIPRAP" "Topo" "0" "RIPRAP.dwg")
    (list "ROCK" "ROCK" "Topo" "0" "ROCK.dwg")
    (list "ROCK WITH STRETCH" "ROCK WITH STRETCH" "Topo" "0" "ROCK WITH STRETCH.dwg")
    (list "SD AD" "SD AD" "Topo" "0" "SD AD.dwg")
    (list "SD CB" "SD CB" "Topo" "0" "SD CB.dwg")
    (list "SD CB 2_5A" "SD CB 2_5A" "Topo" "0" "SD CB 2_5A.dwg")
    (list "SD CB 3AC" "SD CB 3AC" "Topo" "0" "SD CB 3AC.dwg")
    (list "SD CB 4A" "SD CB 4A" "Topo" "0" "SD CB 4A.dwg")
    (list "SD CB 4AC" "SD CB 4AC" "Topo" "0" "SD CB 4AC.dwg")
    (list "SD CB 4ACCC" "SD CB 4ACCC" "Topo" "0" "SD CB 4ACCC.dwg")
    (list "SD CB ACCC" "SD CB ACCC" "Topo" "0" "SD CB ACCC.dwg")
    (list "SD CB G3" "SD CB G3" "Topo" "0" "SD CB G3.dwg")
    (list "SD DI" "SD DI" "Topo" "0" "SD DI.dwg")
    (list "SD FLARED" "SD FLARED" "Topo" "0" "SD FLARED.DWG")
    (list "SD MH" "SD MH" "Topo" "0" "SD MH.DWG")
    (list "SD MH 48 60" "SD MH 48 60" "Topo" "0" "SD MH 48 60.dwg")
    (list "SD ROOF DRAIN ARR" "SD ROOF DRAIN ARR" "Topo" "0" "SD ROOF DRAIN ARR.dwg")
    (list "SD ROOF DRAIN SPLASHBLOCK" "SD ROOF DRAIN SPLASHBLOCK" "Topo" "0" "SD ROOF DRAIN SPLASHBLOCK.dwg")
    (list "SD ROOF DRAIN" "SD ROOF DRAIN" "Topo" "0" "SD ROOF DRAIN.dwg")
    (list "SD SIDE OPENING" "SD SIDE OPENING" "Topo" "0" "SD SIDE OPENING.dwg")
    (list "SD TREEPOD 04X04" "SD TREEPOD 04X04" "Topo" "0" "SD TREEPOD 04X04.dwg")
    (list "SD TREEPOD 04X08" "SD TREEPOD 04X08" "Topo" "0" "SD TREEPOD 04X08.dwg")
    (list "SD TREEPOD 06X10" "SD TREEPOD 06X10" "Topo" "0" "SD TREEPOD 06X10.dwg")
    (list "SD TRENCH" "SD TRENCH" "Topo" "0" "SD TRENCH.DWG")
    (list "SS MH" "SS MH" "Topo" "0" "SS MH.DWG")
    (list "SS MH 48 60" "SS MH 48 60" "Topo" "0" "SS MH 48 60.dwg")
    (list "VAULT B9" "VAULT B9" "Topo" "0" "VAULT B9.DWG")
    (list "VAULT CUSTOM" "VAULT CUSTOM" "Topo" "0" "VAULT CUSTOM.dwg")
    (list "VALVE" "00 VALVE" "Topo" "0" "00 VALVE.DWG")
    (list "VALVE BLOWOFF" "00 BO" "Topo" "0" "00 BO.dwg")
    (list "VALVE BTFY" "00 BTFY" "Topo" "0" "00 BTFY.dwg")
    (list "VALVE CHECK" "00 CHECK" "Topo" "0" "00 CHECK.dwg")
    (list "VALVE CONTROL" "00 CONTROL" "Topo" "0" "00 CONTROL.dwg")
    (list "VALVE FDC" "00 FDC" "Topo" "0" "00 FDC.dwg")
    (list "VALVE GATE" "00 GATE" "Topo" "0" "00 GATE.dwg")
    (list "VALVE GLOBE" "00 GLOBE" "Topo" "0" "00 GLOBE.dwg")
    (list "VALVE PIV" "00 PIV" "Topo" "0" "00 PIV.dwg")
    (list "VALVE PLUG" "00 PLUG" "Topo" "0" "00 PLUG.dwg")
    (list "VALVE SAFETY" "00 SAFETY" "Topo" "0" "00 SAFETY.dwg")
    (list "VEHICLE DYNAMIC" "VEHICLE DYNAMIC" "Topo" "0" "VEHICLE DYNAMIC.dwg")
    (list "VEHICLE TRUCK FIRE FRONT" "VEHICLE TRUCK FIRE FRONT" "Topo" "0" "VEHICLE TRUCK FIRE FRONT.dwg")
    (list "VEHICLE TRUCK GAS" "VEHICLE TRUCK GAS" "Topo" "0" "VEHICLE TRUCK GAS.dwg")
    (list "WATER ASSEMBLY" "WATER ASSEMBLY" "Topo" "0" "WATER ASSEMBLY.dwg")
    (list "WATER BFP" "WATER BFP" "Topo" "0" "WATER BFP.dwg")
    (list "WATER FIRE HYDRANT" "00 FH" "Topo" "0" "00 FH.dwg")
    (list "WATER HOSE BIBB" "00 HOSE BIBB" "Topo" "0" "00 HOSE BIBB.dwg")
    (list "WATER IRR NOZZLE" "IRR NOZZLE" "Topo" "0" "IRR NOZZLE.dwg")
    (list "WATER SERVICE" "WATER SERVICE" "Topo" "0" "WATER SERVICE.dwg")
    (list "WATER SERVICE SINGLE" "WATER SERVICE SINGLE" "Topo" "0" "WATER SERVICE SINGLE.dwg")
    (list "WATER SERVICE DOUBLE" "WATER SERVICE DOUBLE" "Topo" "0" "WATER SERVICE DOUBLE.dwg")
    (list "WATER DRINKING FOUNTAIN" "WATER DRINKING FOUNTAIN" "Topo" "0" "WATER DRINKING FOUNTAIN.dwg")
    (list "WATER STOP" "WATERSTOP" "Topo" "0" "WATERSTOP.dwg")
    (list "WATER SURFACE ELEVATION" "WATER SURFACE ELEVATION" "Topo" "0" "WATER SURFACE ELEVATION.DWG")
    (list "WELL" "WELL" "Topo" "0" "WELL.dwg")
    (list "00 EL 11 22 45" "00 EL 11 22 45" "Topo" "0" "00 EL 11 22 45.dwg")
    (list "00 EL 45 DOUBLE" "00 EL 45 DOUBLE" "Topo" "0" "00 EL 45 DOUBLE.DWG")
    (list "00 TEE CROSS" "00 TEE CROSS" "Topo" "0" "00 TEE CROSS.dwg")
    (list "00 TEE UP DN" "00 TEE UP DN" "Topo" "0" "00 TEE UP DN.dwg")
    (list "00 EL UP DN" "00 EL UP DN" "Topo" "0" "00 EL UP DN.dwg")
    (list "00 FLOW METER FLG" "00 FLOW METER FLG" "Topo" "0" "00 FLOW METER FLG.dwg")
    (list "00 MIXER STATIC" "MIXER STATIC" "Topo" "0" "MIXER STATIC.dwg")
    (list "00 PIPE STAND" "00 PIPE STAND" "Topo" "0" "00 PIPE STAND.dwg")
    (list "00 RED" "00 RED" "Topo" "0" "00 RED.DWG")
    (list "00 SPOOL FLG" "00 SPOOL FLG" "Topo" "0" "00 SPOOL FLG.dwg")
    (list "00 BOLT ANCHOR ROD DYNAMIC" "BOLT ANCHOR ROD DYNAMIC" "Topo" "0" "BOLT ANCHOR ROD DYNAMIC.dwg")
    (list "00 BOLT HEX DYNAMIC" "BOLT HEX DYNAMIC" "Topo" "0" "BOLT HEX DYNAMIC.dwg")
    (list "00 SCREW DYNAMIC" "SCREW DYNAMIC" "Topo" "0" "SCREW DYNAMIC.dwg")
    ;; -- TREE (66 blocks) --
    (list "Tree" "TREE SECTION" "Tree" "0" "TREE SECTION.dwg")
    (list "Tree - Various - Plan & Elevation" "TREE DYNAMIC" "Tree" "0" "TREE DYNAMIC.dwg")
    (list "Tree - Save" "TREE SAVE" "Tree" "0" "TREE SAVE.dwg")
    (list "Tree - Remove" "TREE REMOVE" "Tree" "0" "TREE REMOVE.dwg")
    (list "Tree - 02\"" "TREE 02" "Tree" "0" "TREE 02.dwg")
    (list "Tree - 03\"" "TREE 03" "Tree" "0" "TREE 03.dwg")
    (list "Tree - 04\"" "TREE 04" "Tree" "0" "TREE 04.dwg")
    (list "Tree - 05\"" "TREE 05" "Tree" "0" "TREE 05.dwg")
    (list "Tree - 06\"" "TREE 06" "Tree" "0" "TREE 06.dwg")
    (list "Tree - 07\"" "TREE 07" "Tree" "0" "TREE 07.dwg")
    (list "Tree - 08\"" "TREE 08" "Tree" "0" "TREE 08.dwg")
    (list "Tree - 09\"" "TREE 09" "Tree" "0" "TREE 09.dwg")
    (list "Tree - 10\"" "TREE 10" "Tree" "0" "TREE 10.dwg")
    (list "Tree - 11\"" "TREE 11" "Tree" "0" "TREE 11.dwg")
    (list "Tree - 12\"" "TREE 12" "Tree" "0" "TREE 12.dwg")
    (list "Tree - 13\"" "TREE 13" "Tree" "0" "TREE 13.dwg")
    (list "Tree - 14\"" "TREE 14" "Tree" "0" "TREE 14.dwg")
    (list "Tree - 15\"" "TREE 15" "Tree" "0" "TREE 15.dwg")
    (list "Tree - 16\"" "TREE 16" "Tree" "0" "TREE 16.dwg")
    (list "Tree - 20\"" "TREE 20" "Tree" "0" "TREE 20.dwg")
    (list "Tree - 17\"" "TREE 17" "Tree" "0" "TREE 17.dwg")
    (list "Tree - 18\"" "TREE 18" "Tree" "0" "TREE 18.dwg")
    (list "Tree - 19\"" "TREE 19" "Tree" "0" "TREE 19.dwg")
    (list "Tree - 21\"" "TREE 21" "Tree" "0" "TREE 21.dwg")
    (list "Tree - 22\"" "TREE 22" "Tree" "0" "TREE 22.dwg")
    (list "Tree - 23\"" "TREE 23" "Tree" "0" "TREE 23.dwg")
    (list "Tree - 25\"" "TREE 25" "Tree" "0" "TREE 25.dwg")
    (list "Tree - 26\"" "TREE 26" "Tree" "0" "TREE 26.dwg")
    (list "Tree - 27\"" "TREE 27" "Tree" "0" "TREE 27.dwg")
    (list "Tree - 28\"" "TREE 28" "Tree" "0" "TREE 28.dwg")
    (list "Tree - 29\"" "TREE 29" "Tree" "0" "TREE 29.dwg")
    (list "Tree - 24\"" "TREE 24" "Tree" "0" "TREE 24.dwg")
    (list "Tree - 30\"" "TREE 30" "Tree" "0" "TREE 30.dwg")
    (list "Tree - 31\"" "TREE 31" "Tree" "0" "TREE 31.dwg")
    (list "Tree - 32\"" "TREE 32" "Tree" "0" "TREE 32.dwg")
    (list "Tree - 33\"" "TREE 33" "Tree" "0" "TREE 33.dwg")
    (list "Tree - 34\"" "TREE 34" "Tree" "0" "TREE 34.dwg")
    (list "Tree - 35\"" "TREE 35" "Tree" "0" "TREE 35.dwg")
    (list "Tree - 36\"" "TREE 36" "Tree" "0" "TREE 36.dwg")
    (list "Tree - 37\"" "TREE 37" "Tree" "0" "TREE 37.dwg")
    (list "Tree - 38\"" "TREE 38" "Tree" "0" "TREE 38.dwg")
    (list "Tree - 39\"" "TREE 39" "Tree" "0" "TREE 39.dwg")
    (list "Tree - 40\"" "TREE 40" "Tree" "0" "TREE 40.dwg")
    (list "Tree - 41\"" "TREE 41" "Tree" "0" "TREE 41.dwg")
    (list "Tree - 42\"" "TREE 42" "Tree" "0" "TREE 42.dwg")
    (list "Tree - 43\"" "TREE 43" "Tree" "0" "TREE 43.dwg")
    (list "Tree - 44\"" "TREE 44" "Tree" "0" "TREE 44.dwg")
    (list "Tree - 45\"" "TREE 45" "Tree" "0" "TREE 45.dwg")
    (list "Tree - 46\"" "TREE 46" "Tree" "0" "TREE 46.dwg")
    (list "Tree - 47\"" "TREE 47" "Tree" "0" "TREE 47.dwg")
    (list "Tree - 48\"" "TREE 48" "Tree" "0" "TREE 48.dwg")
    (list "Tree - 49\"" "TREE 49" "Tree" "0" "TREE 49.dwg")
    (list "Tree - 50\"" "TREE 50" "Tree" "0" "TREE 50.dwg")
    (list "Tree - 51\"" "TREE 50" "Tree" "0" "TREE 50.dwg")
    (list "Tree - 52\"" "TREE 52" "Tree" "0" "TREE 52.dwg")
    (list "Tree - 53\"" "TREE 53" "Tree" "0" "TREE 53.dwg")
    (list "Tree - 54\"" "TREE 54" "Tree" "0" "TREE 54.dwg")
    (list "Tree - 55\"" "TREE 55" "Tree" "0" "TREE 55.dwg")
    (list "Tree - 56\"" "TREE 56" "Tree" "0" "TREE 56.dwg")
    (list "Tree - 57\"" "TREE 57" "Tree" "0" "TREE 57.dwg")
    (list "Tree - 58\"" "TREE 58" "Tree" "0" "TREE 58.dwg")
    (list "Tree - 59\"" "TREE 59" "Tree" "0" "TREE 59.dwg")
    (list "Tree - 60\"" "TREE 60" "Tree" "0" "TREE 60.dwg")
    (list "Tree - 61\"" "TREE 61" "Tree" "0" "TREE 61.dwg")
    (list "Tree - 62\"" "TREE 62" "Tree" "0" "TREE 62.dwg")
    (list "Tree - 72\"" "TREE 72" "Tree" "0" "TREE 72.dwg")
    ;; -- UTILITIES (34 blocks) --
    (list "Note - Underground Utility Information Provided by Others" "NOTE UTILITY BY OTHERS" "Utilities" "0" "NOTE UTILITY BY OTHERS.dwg")
    (list "Note - Storm Drain - Place Under Coordinate Table" "NOTE SD" "Utilities" "0" "NOTE SD.dwg")
    (list "Stamp - Pothole - Storm Drain" "STAMP POTHOLE SD" "Utilities" "0" "STAMP POTHOLE SD.dwg")
    (list "Stamp - Sheet Will Be Prepared Durning the Construction Document Phase of the Project" "STAMP SHEET COMPLETE CONSTRUCTION PHASE" "Utilities" "0" "STAMP SHEET COMPLETE CONSTRUCTION PHASE.dwg")
    (list "Wiggle" "WIGGLE" "Utilities" "0" "WIGGLE.dwg")
    (list "End Cap" "00 CAP" "Utilities" "0" "00 CAP.DWG")
    (list "Flow Arrow - Dynamic" "ARR FLOW2" "Utilities" "0" "ARR FLOW2.dwg")
    (list "Flared End Section  - 6\", 8\", 12\", 18\", 24\", 36\"" "SD FLARED" "Utilities" "0" "SD FLARED.DWG")
    (list "Trench Drain" "SD TRENCH" "Utilities" "0" "SD TRENCH.DWG")
    (list "Cleanout" "00 CLEANOUT" "Utilities" "0" "00 CLEANOUT.DWG")
    (list "Storm Drain Catch Basin - 2 1/2A" "SD CB 2_5A" "Utilities" "0" "SD CB 2_5A.dwg")
    (list "Storm Drain Catch Basin - 3AC" "SD CB 3AC" "Utilities" "0" "SD CB 3AC.dwg")
    (list "Storm Drain Catch Basin - 4A" "SD CB 4A" "Utilities" "0" "SD CB 4A.dwg")
    (list "Storm Drain Catch Basin - 4AC" "SD CB 4AC" "Utilities" "0" "SD CB 4AC.dwg")
    (list "Storm Drain Catch Basin - ACCC (Contra Costa County)" "SD CB ACCC" "Utilities" "0" "SD CB ACCC.dwg")
    (list "Storm Drain Catch Basin - G3" "SD CB G3" "Utilities" "0" "SD CB G3.dwg")
    (list "Storm Drain Treepod 04x04" "SD TREEPOD 04X04" "Utilities" "0" "SD TREEPOD 04X04.dwg")
    (list "Storm Drain Treepod 04x08" "SD TREEPOD 04X08" "Utilities" "0" "SD TREEPOD 04X08.dwg")
    (list "Storm Drain Treepod 06x10" "SD TREEPOD 06X10" "Utilities" "0" "SD TREEPOD 06X10.dwg")
    (list "Storm Drain Inlet" "SD DI" "Utilities" "0" "SD DI.dwg")
    (list "Storm Drain Side Opening" "SD SIDE OPENING" "Utilities" "0" "SD SIDE OPENING.dwg")
    (list "Storm Drain Manhole" "SD MH" "Utilities" "0" "SD MH.DWG")
    (list "Storm Drain Manhole - 48\" & 60\"" "SD MH 48 60" "Utilities" "0" "SD MH 48 60.dwg")
    (list "Rip Rap At End of Storm Drain" "RIPRAP" "Utilities" "0" "RIPRAP.dwg")
    (list "Sanitary Sewer Manhole" "SS MH" "Utilities" "0" "SS MH.DWG")
    (list "Sanitary Sewer Manhole - 48\" & 60\"" "SS MH 48 60" "Utilities" "0" "SS MH 48 60.dwg")
    (list "Roof Drain" "SD ROOF DRAIN" "Utilities" "0" "SD ROOF DRAIN.dwg")
    (list "Roof Drain Splash Block" "SD ROOF DRAIN SPLASHBLOCK" "Utilities" "0" "SD ROOF DRAIN SPLASHBLOCK.dwg")
    (list "Roof Drain Arrow" "SD ROOF DRAIN ARR" "Utilities" "0" "SD ROOF DRAIN ARR.dwg")
    (list "Vault - B9" "VAULT B9" "Utilities" "0" "VAULT B9.DWG")
    (list "Vault - Custom" "VAULT CUSTOM" "Utilities" "0" "VAULT CUSTOM.dwg")
    (list "Profile - Catch Basin & Drain Inlet" "PRO DI" "Utilities" "0" "PRO DI.DWG")
    (list "Profile - Manhole" "PRO MH" "Utilities" "0" "PRO MH.DWG")
    (list "Profile - Ellipse" "PRO ELLIPSE" "Utilities" "0" "PRO ELLIPSE.DWG")
    ;; -- WATER (26 blocks) --
    (list "Wiggle" "WIGGLE" "Water" "0" "WIGGLE.dwg")
    (list "Cap" "00 CAP" "Water" "0" "00 CAP.DWG")
    (list "Up or Down Elbow" "00 EL UP DN" "Water" "0" "00 EL UP DN.dwg")
    (list "11 1/4, 22 1/2 & 45 Elbow" "00 EL 11 22 45" "Water" "0" "00 EL 11 22 45.dwg")
    (list "Hose Bibb" "00 HOSE BIBB" "Water" "0" "00 HOSE BIBB.dwg")
    (list "Up or Down Tee" "00 TEE UP DN" "Water" "0" "00 TEE UP DN.dwg")
    (list "Tee & Cross" "00 TEE CROSS" "Water" "0" "00 TEE CROSS.dwg")
    (list "Water Service" "WATER SERVICE" "Water" "0" "WATER SERVICE.dwg")
    (list "Water Service - Single B19" "WATER SERVICE SINGLE" "Water" "0" "WATER SERVICE SINGLE.dwg")
    (list "Water Service - Double B19" "WATER SERVICE DOUBLE" "Water" "0" "WATER SERVICE DOUBLE.dwg")
    (list "Valve" "00 VALVE" "Water" "0" "00 VALVE.DWG")
    (list "Fire Hydrant" "00 FH" "Water" "0" "00 FH.DWG")
    (list "Blowoff" "00 BO" "Water" "0" "00 BO.DWG")
    (list "Thrust Block" "ARR THRUST BLOCK" "Water" "0" "ARR THRUST BLOCK.dwg")
    (list "Butterfly Valve" "00 BTFY" "Water" "0" "00 BTFY.dwg")
    (list "Check Valve" "00 CHECK" "Water" "0" "00 CHECK.dwg")
    (list "Control Valve" "00 CONTROL" "Water" "0" "00 CONTROL.dwg")
    (list "Fire Department Connection" "00 FDC" "Water" "0" "00 FDC.dwg")
    (list "Gate Valve" "00 GATE" "Water" "0" "00 GATE.dwg")
    (list " Globe Valve" "00 GLOBE" "Water" "0" "00 GLOBE.dwg")
    (list "Plug Valve" "00 PLUG" "Water" "0" "00 PLUG.dwg")
    (list "Post Indicator Valve" "00 PIV" "Water" "0" "00 PIV.dwg")
    (list "Safety Valve" "00 SAFETY" "Water" "0" "00 SAFETY.dwg")
    (list "Reducer With Or Without Flange" "00 RED" "Water" "0" "00 RED.DWG")
    (list "45 Elbow-2 Pipes" "00 EL 45 DOUBLE" "Water" "0" "00 EL 45 DOUBLE.DWG")
    (list "Water Surface Elevation" "WATER SURFACE ELEVATION" "Water" "0" "WATER SURFACE ELEVATION.DWG")
  )
)


;;;; -- BLOCK CATEGORIES (auto-built from database) -----------------

(defun BR:BLK:Categories (/ cats)
  (setq cats '("ALL"))
  (foreach blk *BR:BLOCKS*
    (if (not (member (nth 2 blk) cats))
      (setq cats (append cats (list (nth 2 blk))))
    )
  )
  cats
)

;;;; -- BLOCK ACCESSORS ---------------------------------------------

(defun BR:BLK:Disp   (e) (nth 0 e))   ; display name
(defun BR:BLK:Name   (e) (nth 1 e))   ; block name
(defun BR:BLK:Cat    (e) (nth 2 e))   ; category
(defun BR:BLK:Layer  (e) (nth 3 e))   ; target layer
(defun BR:BLK:Source (e) (nth 4 e))   ; source file relative path


;;;; -- FILTER LOGIC ------------------------------------------------

;; Return filtered block list based on category and search string.
;; Category "ALL" means no category filter.
;; Search is case-insensitive substring match on display name.
(defun BR:BLK:Filter (cat search / result blk upsearch)
  (setq result   nil
        upsearch (strcase search))
  (foreach blk *BR:BLOCKS*
    (if (and
          (or (= cat "ALL") (= (BR:BLK:Cat blk) cat))
          (or (= search "")
              (vl-string-search upsearch (strcase (BR:BLK:Disp blk))))
        )
      (setq result (append result (list blk)))
    )
  )
  result
)


;;;; -- INSERT OPERATION --------------------------------------------

;; Insert a block from the library.
;; - Ensures the block definition is loaded (from source file if needed)
;; - Sets target layer current
;; - Prompts user for insertion point
(defun BR:InsertBlock (blk-entry / src-full blk-name target-layer old-layer)
  (setq blk-name    (BR:BLK:Name blk-entry)
        target-layer (BR:BLK:Layer blk-entry)
        src-full    (strcat *BR:BLK-ROOT* (BR:BLK:Source blk-entry)))

  ;; Ensure source file exists
  (if (and (> (strlen (BR:BLK:Source blk-entry)) 0)
           (not (findfile src-full)))
    (progn
      (alert
        (strcat "Block source file not found:\n\n" src-full))
      nil
    )
    (progn
      ;; Set target layer current (create if needed)
      (if (and target-layer (> (strlen target-layer) 0))
        (progn
          (setq old-layer (getvar "CLAYER"))
          (command "._-LAYER" "_M" target-layer "")
        )
      )
      ;; Insert -- AutoCAD will prompt for insertion point, scale, rotation
      (if (> (strlen (BR:BLK:Source blk-entry)) 0)
        (command "._-INSERT" src-full)
        (command "._-INSERT" blk-name)
      )
      ;; Wait for user to complete insertion
      (while (> (getvar "CMDACTIVE") 0) (command pause))
      ;; Restore layer
      (if old-layer
        (setvar "CLAYER" old-layer)
      )
      (princ (strcat "\n  Inserted: " blk-name))
      t
    )
  )
)


;;;; -- DCL DIALOG --------------------------------------------------

;; Filtered display list -- tracks which *BR:BLOCKS* entries are shown
(setq *BR:BLK-FILTERED* nil)

(defun BR:INS:RefreshList (cat search / filtered)
  (setq filtered (BR:BLK:Filter cat search))
  (setq *BR:BLK-FILTERED* filtered)
  (start_list "blk_list")
  (foreach blk filtered
    (add_list
      (strcat "[" (BR:BLK:Cat blk) "]  " (BR:BLK:Disp blk)))
  )
  (end_list)
  ;; Clear detail tiles
  (set_tile "blk_name"   "Block :  ...")
  (set_tile "blk_layer"  "Layer :  ...")
  (set_tile "blk_source" "Source :  ...")
)

(defun BR:INS:ShowDetail (idx / blk)
  (if (and (>= idx 0) (< idx (length *BR:BLK-FILTERED*)))
    (progn
      (setq blk (nth idx *BR:BLK-FILTERED*))
      (set_tile "blk_name"
        (strcat "Block :  " (BR:BLK:Name blk)))
      (set_tile "blk_layer"
        (strcat "Layer :  " (BR:BLK:Layer blk)))
      (set_tile "blk_source"
        (strcat "Source :  " (BR:BLK:Source blk)))
    )
  )
)

(defun BR:InsertDCL (/ dcl-path dcl-id done d-catidx d-blkidx d-search
                       cats cat-name blk-entry)

  (setq dcl-path (findfile "BR_Insert.dcl"))
  (if (null dcl-path)
    (progn
      (alert
        (strcat "BR_Insert.dcl not found.\n\n"
                "Make sure BR_Insert.dcl is in the same folder as the LSP files\n"
                "and that folder is on AutoCAD's support path."))
      (exit)
    )
  )

  (setq d-catidx 0
        d-blkidx -1
        d-search "")

  (setq dcl-id (load_dialog dcl-path))
  (if (< dcl-id 0)
    (progn (alert (strcat "Cannot load DCL:\n" dcl-path)) (exit))
  )
  (if (not (new_dialog "br_insert" dcl-id))
    (progn
      (unload_dialog dcl-id)
      (alert "Cannot initialize br_insert dialog.")
      (exit)
    )
  )

  ;; Populate category dropdown
  (setq cats (BR:BLK:Categories))
  (start_list "blk_category")
  (foreach c cats (add_list c))
  (end_list)
  (set_tile "blk_category" "0")

  ;; Initial block list (all)
  (BR:INS:RefreshList "ALL" "")

  ;; Actions
  (action_tile "blk_category"
    (strcat
      "(setq d-catidx (BR:DCL:SafeIndex $value))"
      "(BR:INS:RefreshList"
      "  (if (and (>= d-catidx 0) (< d-catidx (length cats)))"
      "    (nth d-catidx cats)"
      "    \"ALL\")"
      "  d-search)"))

  (action_tile "blk_search"
    (strcat
      "(setq d-search (BR:SafeStr $value))"
      "(BR:INS:RefreshList"
      "  (if (and (>= d-catidx 0) (< d-catidx (length cats)))"
      "    (nth d-catidx cats)"
      "    \"ALL\")"
      "  d-search)"))

  (action_tile "blk_list"
    (strcat
      "(setq d-blkidx (BR:DCL:SafeIndex $value))"
      "(BR:INS:ShowDetail d-blkidx)"
      "(if (= $reason 4) (done_dialog 1))"))

  (action_tile "accept" "(done_dialog 1)")
  (action_tile "cancel" "(done_dialog 0)")

  (setq done (start_dialog))
  (unload_dialog dcl-id)

  ;; -- Act on result ---------------------------------------------
  (if (and (= done 1) (>= d-blkidx 0) (< d-blkidx (length *BR:BLK-FILTERED*)))
    (progn
      (setq blk-entry (nth d-blkidx *BR:BLK-FILTERED*))
      (BR:InsertBlock blk-entry)
    )
    (if (and (= done 1) (< d-blkidx 0))
      (alert "Please select a block from the list first.")
    )
  )
)


;;;; -- COMMAND ------------------------------------------------------

(defun C:BR_INS (/ *error* _olderr _saved _undoFlag)
  (vl-load-com)
  (setq _saved  (BR:SaveSysvars '("CMDECHO" "CLAYER"))
        _olderr *error*)
  (defun *error* (msg)
    (if (and msg (not (wcmatch (strcase msg) "*CANCEL*,*QUIT*")))
      (princ (strcat "\nError: " msg))
    )
    (BR:EndUndo _undoFlag)
    (BR:RestoreSysvars _saved)
    (setq *error* _olderr)
    (princ)
  )
  (setvar "CMDECHO" 0)
  (setq _undoFlag (BR:BeginUndo))

  (BR:InsertDCL)

  (BR:EndUndo _undoFlag)
  (BR:RestoreSysvars _saved)
  (setq *error* _olderr)
  (princ)
)


;;;; -- MODULE LOADED -----------------------------------------------

(princ "\n  BR_Insert module loaded.  Command: BR_INS")
(princ)

;;; End of BR_Insert.lsp
